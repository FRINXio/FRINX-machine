module Cisco-IOS-XR-infra-infra-locale-cfg {

  /*** NAMESPACE / PREFIX DEFINITION ***/

  namespace "http://cisco.com/ns/yang"+
    "/Cisco-IOS-XR-infra-infra-locale-cfg";


  prefix "infra-infra-locale-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-infra-locale package configuration.

     This module contains definitions
     for the following management objects:
       locale: Define the geographical locale

     Copyright (c) 2013-2016 by Cisco Systems, Inc.
     All rights reserved.";

  revision "2015-11-09" {
    description
      "IOS XR 6.0 revision.";
  }

  typedef Locale-country {
    type enumeration {
      enum ad {
        value 1;
        description "Andorra";
      }
      enum ae {
        value 2;
        description "United Arab Emirates";
      }
      enum af {
        value 3;
        description "Afghanistan";
      }
      enum ag {
        value 4;
        description "Antigua and Barbuda";
      }
      enum ai {
        value 5;
        description "Anguilla";
      }
      enum al {
        value 6;
        description "Albania";
      }
      enum am {
        value 7;
        description "Armenia";
      }
      enum an {
        value 8;
        description "Netherlands Antilles";
      }
      enum ao {
        value 9;
        description "Angola";
      }
      enum aq {
        value 10;
        description "Antarctica";
      }
      enum ar {
        value 11;
        description "Argentina";
      }
      enum as {
        value 12;
        description "American Samoa";
      }
      enum at {
        value 13;
        description "Austria";
      }
      enum au {
        value 14;
        description "Australia";
      }
      enum aw {
        value 15;
        description "Aruba";
      }
      enum az {
        value 16;
        description "Azerbaijan";
      }
      enum ba {
        value 17;
        description "Bosnia and Herzegovina";
      }
      enum bb {
        value 18;
        description "Barbados";
      }
      enum bd {
        value 19;
        description "Bangladesh";
      }
      enum be {
        value 20;
        description "Belgium";
      }
      enum bf {
        value 21;
        description "Burkina Faso";
      }
      enum bg {
        value 22;
        description "Bulgaria";
      }
      enum bh {
        value 23;
        description "Bahrain";
      }
      enum bi {
        value 24;
        description "Burundi";
      }
      enum bj {
        value 25;
        description "Benin";
      }
      enum bm {
        value 26;
        description "Bermuda";
      }
      enum bn {
        value 27;
        description "Brunei Darussalam";
      }
      enum bo {
        value 28;
        description "Bolivia";
      }
      enum br {
        value 29;
        description "Brazil";
      }
      enum bs {
        value 30;
        description "Bahamas";
      }
      enum bt {
        value 31;
        description "Bhutan";
      }
      enum bv {
        value 32;
        description "Bouvet Island";
      }
      enum bw {
        value 33;
        description "Botswana";
      }
      enum by {
        value 34;
        description "Belarus";
      }
      enum bz {
        value 35;
        description "Belize";
      }
      enum ca {
        value 36;
        description "Canada";
      }
      enum cc {
        value 37;
        description "Cocos (Keeling) Islands";
      }
      enum cd {
        value 38;
        description "Congo, The Democratic Republic of the (Zaire)";
      }
      enum cf {
        value 39;
        description "Central African Republic";
      }
      enum cg {
        value 40;
        description "Congo";
      }
      enum ch {
        value 41;
        description "Switzerland";
      }
      enum ci {
        value 42;
        description "Cote D'Ivoire";
      }
      enum ck {
        value 43;
        description "Cook Islands";
      }
      enum cl {
        value 44;
        description "Chile";
      }
      enum cm {
        value 45;
        description "Cameroon";
      }
      enum cn {
        value 46;
        description "China";
      }
      enum co {
        value 47;
        description "Colombia";
      }
      enum cr {
        value 48;
        description "Costa Rica";
      }
      enum cu {
        value 49;
        description "Cuba";
      }
      enum cv {
        value 50;
        description "Cape Verde";
      }
      enum cx {
        value 51;
        description "Christmas Island";
      }
      enum cy {
        value 52;
        description "Cyprus";
      }
      enum cz {
        value 53;
        description "Czech Republic";
      }
      enum de {
        value 54;
        description "Germany";
      }
      enum dj {
        value 55;
        description "Djibouti";
      }
      enum dk {
        value 56;
        description "Denmark";
      }
      enum dm {
        value 57;
        description "Dominica";
      }
      enum do {
        value 58;
        description "Dominican Republic";
      }
      enum dz {
        value 59;
        description "Algeria";
      }
      enum ec {
        value 60;
        description "Ecuador";
      }
      enum ee {
        value 61;
        description "Estonia";
      }
      enum eg {
        value 62;
        description "Egypt";
      }
      enum eh {
        value 63;
        description "Western Sahara";
      }
      enum er {
        value 64;
        description "Eritrea";
      }
      enum es {
        value 65;
        description "Spain";
      }
      enum et {
        value 66;
        description "Ethiopia";
      }
      enum fi {
        value 67;
        description "Finland";
      }
      enum fj {
        value 68;
        description "Fiji";
      }
      enum fk {
        value 69;
        description "Falkland Islands (Malvinas)";
      }
      enum fm {
        value 70;
        description "Micronesia, Federated States of";
      }
      enum fo {
        value 71;
        description "Faroe Islands";
      }
      enum fr {
        value 72;
        description "France";
      }
      enum ga {
        value 73;
        description "Gabon";
      }
      enum gb {
        value 74;
        description "United Kingdom";
      }
      enum gd {
        value 75;
        description "Grenada";
      }
      enum ge {
        value 76;
        description "Georgia";
      }
      enum gf {
        value 77;
        description "French Guiana";
      }
      enum gh {
        value 78;
        description "Ghana";
      }
      enum gi {
        value 79;
        description "Gibraltar";
      }
      enum gl {
        value 80;
        description "Greenland";
      }
      enum gm {
        value 81;
        description "Gambia";
      }
      enum gn {
        value 82;
        description "Guinea";
      }
      enum gp {
        value 83;
        description "Guadeloupe";
      }
      enum gq {
        value 84;
        description "Equatorial Guinea";
      }
      enum gr {
        value 85;
        description "Greece";
      }
      enum gs {
        value 86;
        description "South Georgia and the South Sandwich Islands";
      }
      enum gt {
        value 87;
        description "Guatemala";
      }
      enum gu {
        value 88;
        description "Guam";
      }
      enum gw {
        value 89;
        description "Guinea Bissau";
      }
      enum gy {
        value 90;
        description "Guyana";
      }
      enum hk {
        value 91;
        description "Hong Kong";
      }
      enum hm {
        value 92;
        description "Heard Island and McDonald Islands";
      }
      enum hn {
        value 93;
        description "Honduras";
      }
      enum hr {
        value 94;
        description "Croatia";
      }
      enum ht {
        value 95;
        description "Haiti";
      }
      enum hu {
        value 96;
        description "Hungary";
      }
      enum id {
        value 97;
        description "Indonesia";
      }
      enum ie {
        value 98;
        description "Ireland";
      }
      enum il {
        value 99;
        description "Israel";
      }
      enum in {
        value 100;
        description "India";
      }
      enum io {
        value 101;
        description "British Indian Ocean Territory";
      }
      enum iq {
        value 102;
        description "Iraq";
      }
      enum ir {
        value 103;
        description "Iran, Islamic Republic of";
      }
      enum is {
        value 104;
        description "Iceland";
      }
      enum it {
        value 105;
        description "Italy";
      }
      enum jm {
        value 106;
        description "Jamaica";
      }
      enum jo {
        value 107;
        description "Jordan";
      }
      enum jp {
        value 108;
        description "Japan";
      }
      enum ke {
        value 109;
        description "Kenya";
      }
      enum kg {
        value 110;
        description "Kyrgyzstan";
      }
      enum kh {
        value 111;
        description "Cambodia";
      }
      enum ki {
        value 112;
        description "Kiribati";
      }
      enum km {
        value 113;
        description "Comoros";
      }
      enum kn {
        value 114;
        description "Saint Kitts and Nevis";
      }
      enum kp {
        value 115;
        description "Korea, Democratic People's Republic of";
      }
      enum kr {
        value 116;
        description "Korea, Republic of";
      }
      enum kw {
        value 117;
        description "Kuwait";
      }
      enum ky {
        value 118;
        description "Cayman Islands";
      }
      enum kz {
        value 119;
        description "Kazakstan";
      }
      enum la {
        value 120;
        description "Lao People's Democratic Republic";
      }
      enum lb {
        value 121;
        description "Lebanon";
      }
      enum lc {
        value 122;
        description "Saint Lucia";
      }
      enum li {
        value 123;
        description "Liechtenstein";
      }
      enum lk {
        value 124;
        description "Sri Lanka";
      }
      enum lr {
        value 125;
        description "Liberia";
      }
      enum ls {
        value 126;
        description "Lesotho";
      }
      enum lt {
        value 127;
        description "Lithuania";
      }
      enum lu {
        value 128;
        description "Luxembourg";
      }
      enum lv {
        value 129;
        description "Latvia";
      }
      enum ly {
        value 130;
        description "Libyan Arab Jamahiriya";
      }
      enum ma {
        value 131;
        description "Morocco";
      }
      enum mc {
        value 132;
        description "Monaco";
      }
      enum md {
        value 133;
        description "Moldova, Republic of";
      }
      enum mg {
        value 134;
        description "Madagascar";
      }
      enum mh {
        value 135;
        description "Marshall Islands";
      }
      enum mk {
        value 136;
        description "Macedonia, The Former Yugoslav Republic of";
      }
      enum ml {
        value 137;
        description "Mali";
      }
      enum mm {
        value 138;
        description "Myanmar";
      }
      enum mn {
        value 139;
        description "Mongolia";
      }
      enum mo {
        value 140;
        description "Macau";
      }
      enum mp {
        value 141;
        description "Northern Mariana Islands";
      }
      enum mq {
        value 142;
        description "Martinique";
      }
      enum mr {
        value 143;
        description "Mauritania";
      }
      enum ms {
        value 144;
        description "Montserrat";
      }
      enum mt {
        value 145;
        description "Malta";
      }
      enum mu {
        value 146;
        description "Mauritius";
      }
      enum mv {
        value 147;
        description "Maldives";
      }
      enum mw {
        value 148;
        description "Malawi";
      }
      enum mx {
        value 149;
        description "Mexico";
      }
      enum my {
        value 150;
        description "Malaysia";
      }
      enum mz {
        value 151;
        description "Mozambique";
      }
      enum na {
        value 152;
        description "Namibia";
      }
      enum nc {
        value 153;
        description "New Caledonia";
      }
      enum ne {
        value 154;
        description "Niger";
      }
      enum nf {
        value 155;
        description "Norfolk Island";
      }
      enum ng {
        value 156;
        description "Nigeria";
      }
      enum ni {
        value 157;
        description "Nicaragua";
      }
      enum nl {
        value 158;
        description "Netherlands";
      }
      enum no {
        value 159;
        description "Norway";
      }
      enum np {
        value 160;
        description "Nepal";
      }
      enum nr {
        value 161;
        description "Nauru";
      }
      enum nu {
        value 162;
        description "Niue";
      }
      enum nz {
        value 163;
        description "New Zealand";
      }
      enum om {
        value 164;
        description "Oman";
      }
      enum pa {
        value 165;
        description "Panama";
      }
      enum pe {
        value 166;
        description "Peru";
      }
      enum pf {
        value 167;
        description "French Polynesia";
      }
      enum pg {
        value 168;
        description "Papua New Guinea";
      }
      enum ph {
        value 169;
        description "Philippines";
      }
      enum pk {
        value 170;
        description "Pakistan";
      }
      enum pl {
        value 171;
        description "Poland";
      }
      enum pm {
        value 172;
        description "Saint Pierre and Miquelon";
      }
      enum pn {
        value 173;
        description "Pitcairn";
      }
      enum pr {
        value 174;
        description "Puerto Rico";
      }
      enum pt {
        value 175;
        description "Portugal";
      }
      enum pw {
        value 176;
        description "Palau";
      }
      enum py {
        value 177;
        description "Paraguay";
      }
      enum qa {
        value 178;
        description "Qatar";
      }
      enum re {
        value 179;
        description "Reunion";
      }
      enum ro {
        value 180;
        description "Romania";
      }
      enum ru {
        value 181;
        description "Russian Federation";
      }
      enum rw {
        value 182;
        description "Rwanda";
      }
      enum sa {
        value 183;
        description "Saudi Arabia";
      }
      enum sb {
        value 184;
        description "Solomon Islands";
      }
      enum sc {
        value 185;
        description "Seychelles";
      }
      enum sd {
        value 186;
        description "Sudan";
      }
      enum se {
        value 187;
        description "Sweden";
      }
      enum sg {
        value 188;
        description "Singapore";
      }
      enum sh {
        value 189;
        description "Saint Helena";
      }
      enum si {
        value 190;
        description "Slovenia";
      }
      enum sj {
        value 191;
        description "Svalbard and Jan Mayen";
      }
      enum sk {
        value 192;
        description "Slovakia";
      }
      enum sl {
        value 193;
        description "Sierra Leone";
      }
      enum sm {
        value 194;
        description "San Marino";
      }
      enum sn {
        value 195;
        description "Senegal";
      }
      enum so {
        value 196;
        description "Somalia";
      }
      enum sr {
        value 197;
        description "Suriname";
      }
      enum st {
        value 198;
        description "Sao Tome and Principe";
      }
      enum sv {
        value 199;
        description "El Salvador";
      }
      enum sy {
        value 200;
        description "Syrian Arab Republic";
      }
      enum sz {
        value 201;
        description "Swaziland";
      }
      enum tc {
        value 202;
        description "Turks and Caicos Islands";
      }
      enum td {
        value 203;
        description "Chad";
      }
      enum tf {
        value 204;
        description "French Southern Territories";
      }
      enum tg {
        value 205;
        description "Togo";
      }
      enum th {
        value 206;
        description "Thailand";
      }
      enum tj {
        value 207;
        description "Tajikistan";
      }
      enum tk {
        value 208;
        description "Tokelau";
      }
      enum tm {
        value 209;
        description "Turkmenistan";
      }
      enum tn {
        value 210;
        description "Tunisia";
      }
      enum to {
        value 211;
        description "Tonga";
      }
      enum tp {
        value 212;
        description "East Timor";
      }
      enum tr {
        value 213;
        description "Turkey";
      }
      enum tt {
        value 214;
        description "Trinidad and Tobago";
      }
      enum tv {
        value 215;
        description "Tuvalu";
      }
      enum tw {
        value 216;
        description "Taiwan, Province of China";
      }
      enum tz {
        value 217;
        description "Tanzania, United Republic of";
      }
      enum ua {
        value 218;
        description "Ukraine";
      }
      enum ug {
        value 219;
        description "Uganda";
      }
      enum um {
        value 220;
        description "United States Minor Outlying Islands";
      }
      enum us {
        value 221;
        description "United States";
      }
      enum uy {
        value 222;
        description "Uruguay";
      }
      enum uz {
        value 223;
        description "Uzbekistan";
      }
      enum va {
        value 224;
        description "Holy See (Vatican City State)";
      }
      enum vc {
        value 225;
        description "Saint Vincent and The Grenadines";
      }
      enum ve {
        value 226;
        description "Venezuela";
      }
      enum vg {
        value 227;
        description "Virgin Islands, British";
      }
      enum vi {
        value 228;
        description "Virgin Islands, U.S.";
      }
      enum vn {
        value 229;
        description "Vietnam";
      }
      enum vu {
        value 230;
        description "Vanuatu";
      }
      enum wf {
        value 231;
        description "Wallis and Futuna";
      }
      enum ws {
        value 232;
        description "Samoa";
      }
      enum ye {
        value 233;
        description "Yemen";
      }
      enum yt {
        value 234;
        description "Mayotte";
      }
      enum yu {
        value 235;
        description "Yugoslavia";
      }
      enum za {
        value 236;
        description "South Africa";
      }
      enum zm {
        value 237;
        description "Zambia";
      }
      enum zw {
        value 238;
        description "Zimbabwe";
      }
    }
    description "Locale country";
  }
  typedef Locale-language {
    type enumeration {
      enum aa {
        value 1;
        description "Afar";
      }
      enum ab {
        value 2;
        description "Abkhazian";
      }
      enum af {
        value 3;
        description "Afrikaans";
      }
      enum am {
        value 4;
        description "Amharic";
      }
      enum ar {
        value 5;
        description "Arabic";
      }
      enum as {
        value 6;
        description "Assamese";
      }
      enum ay {
        value 7;
        description "Aymara";
      }
      enum az {
        value 8;
        description "Azerbaijani";
      }
      enum ba {
        value 9;
        description "Bashkir";
      }
      enum be {
        value 10;
        description "Byelorussian";
      }
      enum bg {
        value 11;
        description "Bulgarian";
      }
      enum bh {
        value 12;
        description "Bihari";
      }
      enum bi {
        value 13;
        description "Bislama";
      }
      enum bn {
        value 14;
        description "Bengali";
      }
      enum bo {
        value 15;
        description "Tibetan";
      }
      enum br {
        value 16;
        description "Breton";
      }
      enum ca {
        value 17;
        description "Catalan";
      }
      enum co {
        value 18;
        description "Corsican";
      }
      enum cs {
        value 19;
        description "Czech";
      }
      enum cy {
        value 20;
        description "Welsh";
      }
      enum da {
        value 21;
        description "Danish";
      }
      enum de {
        value 22;
        description "German";
      }
      enum dz {
        value 23;
        description "Bhutani";
      }
      enum el {
        value 24;
        description "Greek";
      }
      enum en {
        value 25;
        description "English";
      }
      enum eo {
        value 26;
        description "Esperanto";
      }
      enum es {
        value 27;
        description "Spanish";
      }
      enum et {
        value 28;
        description "Estonian";
      }
      enum eu {
        value 29;
        description "Basque";
      }
      enum fa {
        value 30;
        description "Persian";
      }
      enum fi {
        value 31;
        description "Finnish";
      }
      enum fj {
        value 32;
        description "Fiji";
      }
      enum fo {
        value 33;
        description "Faroese";
      }
      enum fr {
        value 34;
        description "French";
      }
      enum fy {
        value 35;
        description "Frisian";
      }
      enum ga {
        value 36;
        description "Irish";
      }
      enum gd {
        value 37;
        description "Scots Gaelic";
      }
      enum gl {
        value 38;
        description "Galician";
      }
      enum gn {
        value 39;
        description "Guarani";
      }
      enum gu {
        value 40;
        description "Gujarati";
      }
      enum ha {
        value 41;
        description "Hausa";
      }
      enum he {
        value 42;
        description "Hebrew";
      }
      enum hi {
        value 43;
        description "Hindi";
      }
      enum hr {
        value 44;
        description "Croatian";
      }
      enum hu {
        value 45;
        description "Hungarian";
      }
      enum hy {
        value 46;
        description "Armenian";
      }
      enum ia {
        value 47;
        description "Interlingua";
      }
      enum id {
        value 48;
        description "Indonesian";
      }
      enum ie {
        value 49;
        description "Interlingue";
      }
      enum ik {
        value 50;
        description "Inupiak";
      }
      enum is {
        value 51;
        description "Icelandic";
      }
      enum it {
        value 52;
        description "Italian";
      }
      enum iu {
        value 53;
        description "Inuktitut";
      }
      enum ja {
        value 54;
        description "Japanese";
      }
      enum jw {
        value 55;
        description "Javanese";
      }
      enum ka {
        value 56;
        description "Georgian";
      }
      enum kk {
        value 57;
        description "Kazakh";
      }
      enum kl {
        value 58;
        description "Greenlandic";
      }
      enum km {
        value 59;
        description "Cambodian";
      }
      enum kn {
        value 60;
        description "Kannada";
      }
      enum ko {
        value 61;
        description "Korean";
      }
      enum ks {
        value 62;
        description "Kashmiri";
      }
      enum ku {
        value 63;
        description "Kurdish";
      }
      enum ky {
        value 64;
        description "Kirghiz";
      }
      enum la {
        value 65;
        description "Latin";
      }
      enum ln {
        value 66;
        description "Lingala";
      }
      enum lo {
        value 67;
        description "Laothian";
      }
      enum lt {
        value 68;
        description "Lithuanian";
      }
      enum lv {
        value 69;
        description "Latvian, Lettish";
      }
      enum mg {
        value 70;
        description "Malagasy";
      }
      enum mi {
        value 71;
        description "Maori";
      }
      enum mk {
        value 72;
        description "Macedonian";
      }
      enum ml {
        value 73;
        description "Malayalam";
      }
      enum mn {
        value 74;
        description "Mongolian";
      }
      enum mo {
        value 75;
        description "Moldavian";
      }
      enum mr {
        value 76;
        description "Marathi";
      }
      enum ms {
        value 77;
        description "Malay";
      }
      enum mt {
        value 78;
        description "Maltese";
      }
      enum my {
        value 79;
        description "Burmese";
      }
      enum na {
        value 80;
        description "Nauru";
      }
      enum ne {
        value 81;
        description "Nepali";
      }
      enum nl {
        value 82;
        description "Dutch";
      }
      enum no {
        value 83;
        description "Norwegian";
      }
      enum oc {
        value 84;
        description "Occitan";
      }
      enum om {
        value 85;
        description "(Afan) Oromo";
      }
      enum or {
        value 86;
        description "Oriya";
      }
      enum pa {
        value 87;
        description "Punjabi";
      }
      enum pl {
        value 88;
        description "Polish";
      }
      enum ps {
        value 89;
        description "Pashto, Pushto";
      }
      enum pt {
        value 90;
        description "Portuguese";
      }
      enum qu {
        value 91;
        description "Quechua";
      }
      enum rm {
        value 92;
        description "Rhaeto Romance";
      }
      enum rn {
        value 93;
        description "Kirundi";
      }
      enum ro {
        value 94;
        description "Romanian";
      }
      enum ru {
        value 95;
        description "Russian";
      }
      enum rw {
        value 96;
        description "Kinyarwanda";
      }
      enum sa {
        value 97;
        description "Sanskrit";
      }
      enum sd {
        value 98;
        description "Sindhi";
      }
      enum sg {
        value 99;
        description "Sangho";
      }
      enum sh {
        value 100;
        description "Serbo Croatian";
      }
      enum si {
        value 101;
        description "Sinhalese";
      }
      enum sk {
        value 102;
        description "Slovak";
      }
      enum sl {
        value 103;
        description "Slovenian";
      }
      enum sm {
        value 104;
        description "Samoan";
      }
      enum sn {
        value 105;
        description "Shona";
      }
      enum so {
        value 106;
        description "Somali";
      }
      enum sq {
        value 107;
        description "Albanian";
      }
      enum sr {
        value 108;
        description "Serbian";
      }
      enum ss {
        value 109;
        description "Siswati";
      }
      enum st {
        value 110;
        description "Sesotho";
      }
      enum su {
        value 111;
        description "Sundanese";
      }
      enum sv {
        value 112;
        description "Swedish";
      }
      enum sw {
        value 113;
        description "Swahili";
      }
      enum ta {
        value 114;
        description "Tamil";
      }
      enum te {
        value 115;
        description "Telugu";
      }
      enum tg {
        value 116;
        description "Tajik";
      }
      enum th {
        value 117;
        description "Thai";
      }
      enum ti {
        value 118;
        description "Tigrinya";
      }
      enum tk {
        value 119;
        description "Turkmen";
      }
      enum tl {
        value 120;
        description "Tagalog";
      }
      enum tn {
        value 121;
        description "Setswana";
      }
      enum to {
        value 122;
        description "Tonga";
      }
      enum tr {
        value 123;
        description "Turkish";
      }
      enum ts {
        value 124;
        description "Tsonga";
      }
      enum tt {
        value 125;
        description "Tatar";
      }
      enum tw {
        value 126;
        description "Twi";
      }
      enum ug {
        value 127;
        description "Uighur";
      }
      enum uk {
        value 128;
        description "Ukrainian";
      }
      enum ur {
        value 129;
        description "Urdu";
      }
      enum uz {
        value 130;
        description "Uzbek";
      }
      enum vi {
        value 131;
        description "Vietnamese";
      }
      enum vo {
        value 132;
        description "Volapuk";
      }
      enum wo {
        value 133;
        description "Wolof";
      }
      enum xh {
        value 134;
        description "Xhosa";
      }
      enum yi {
        value 135;
        description "Yiddish";
      }
      enum yo {
        value 136;
        description "Yoruba";
      }
      enum za {
        value 137;
        description "Zhuang";
      }
      enum zh {
        value 138;
        description "Chinese";
      }
      enum zu {
        value 139;
        description "Zulu";
      }
    }
    description "Locale language";
  }

  container locale {
    description "Define the geographical locale";
    leaf country {
      type Locale-country;
      description "Name of country locale";
    }
    leaf language {
      type Locale-language;
      description "Name of language locale";
    }
  }
}
