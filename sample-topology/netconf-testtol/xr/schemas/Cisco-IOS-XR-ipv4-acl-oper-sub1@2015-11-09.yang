submodule Cisco-IOS-XR-ipv4-acl-oper-sub1 {

  belongs-to Cisco-IOS-XR-ipv4-acl-oper {
    prefix Cisco-IOS-XR-ipv4-acl-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-acl package operational data.

     Copyright (c) 2013-2016 by Cisco Systems, Inc.
     All rights reserved.";

  revision "2015-11-09" {
    description
      "IOS XR 6.0 revision.";
  }

  typedef Bag-acl-nh-at-status {
    type enumeration {
      enum unknown {
        description "AT State Unknown";
      }
      enum up {
        description "AT State UP";
      }
      enum down {
        description "AT State DOWN";
      }
      enum not-present {
        description "AT State Not Present";
      }
      enum max {
        description "invalid status";
      }
    }
    description "Bag acl nh at status";
  }
  typedef Bag-acl-nh-status {
    type enumeration {
      enum not-present {
        description "State Not Present";
      }
      enum unknown {
        description "State Unknown";
      }
      enum down {
        description "State DOWN";
      }
      enum up {
        description "State UP";
      }
      enum max {
        description "invalid status";
      }
    }
    description "Bag acl nh status";
  }
  typedef Bag-acl-nh {
    type enumeration {
      enum nexthop-none {
        description "Next Hop None";
      }
      enum nexthop-default {
        description "Nexthop Default";
      }
      enum nexthop {
        description "Nexthop";
      }
    }
    description "Bag acl nh";
  }
  typedef Acl-ttl-operator {
    type Acl-port-operator;
    description "Acl ttl operator";
  }
  typedef Acl-plen-operator {
    type Acl-port-operator;
    description "Acl plen operator";
  }
  typedef Acl-tcpflags-operator {
    type enumeration {
      enum match-none {
        description "Match None";
      }
      enum match-all {
        description "Match All";
      }
      enum match-any-old {
        description "Match any old";
      }
      enum match-any {
        description "Match any";
      }
    }
    description "Acl tcpflags operator";
  }
  typedef Acl-log {
    type enumeration {
      enum log-none {
        value 0;
        description "Log None";
      }
      enum log {
        value 1;
        description "Log Regular";
      }
      enum log-input {
        value 2;
        description "Log Input";
      }
    }
    description "Acl log";
  }
  typedef Acl-port-operator {
    type enumeration {
      enum none {
        value 0;
        description "None";
      }
      enum eq {
        value 1;
        description "Equal";
      }
      enum gt {
        value 2;
        description "Greater than";
      }
      enum lt {
        value 3;
        description "Less than";
      }
      enum neq {
        value 4;
        description "Not Equal";
      }
      enum range {
        value 5;
        description "Range";
      }
      enum onebyte {
        value 8;
        description "One Byte";
      }
      enum twobytes {
        value 9;
        description "Two Bytes";
      }
    }
    description "Acl port operator";
  }
  typedef Acl-action {
    type enumeration {
      enum deny {
        value 0;
        description "Deny";
      }
      enum permit {
        value 1;
        description "Permit";
      }
      enum encrypt {
        value 2;
        description "Encrypt";
      }
      enum bypass {
        value 3;
        description "Bypass";
      }
      enum fallthrough {
        value 4;
        description "Fallthrough";
      }
      enum invalid {
        value 5;
        description "Invalid";
      }
    }
    description "Acl action";
  }
  typedef Acl-ace1 {
    type enumeration {
      enum normal {
        description "This is Normal ACE";
      }
      enum remark {
        description "This is Remark ACE";
      }
      enum abf {
        description "This is ABF ACE";
      }
    }
    description "ACE Types";
  }
  typedef Acl-ace {
    type Acl-ace1;
    description "ACE Types";
  }

  grouping IPV4-ACL-EDM-OOR-DETAIL {
    description "Oor deatil config BAG";
    leaf default-max-ac-ls {
      type uint32;
      description "default max configurable acls";
    }
    leaf default-max-ac-es {
      type uint32;
      description "default max configurable aces";
    }
    leaf current-configured-ac-ls {
      type uint32;
      description "Current configured acls";
    }
    leaf current-configured-ac-es {
      type uint32;
      description "Current configured aces";
    }
    leaf current-max-configurable-ac-ls {
      type uint32;
      description "Current max configurable acls";
    }
    leaf current-max-configurable-ac-es {
      type uint32;
      description "Current max configurable aces";
    }
    leaf max-configurable-ac-ls {
      type uint32;
      description "max configurable acls";
    }
    leaf max-configurable-ac-es {
      type uint32;
      description "max configurable aces";
    }
  }

  grouping IPV4-ACL-BAG-HW-NH-INFO {
    description "HW_NH_Info structure";
    leaf next-hop {
      type uint32;
      description "The Next Hop";
    }
    leaf type {
      type Bag-acl-nh;
      description "the next-hop type";
    }
    leaf vrf-name {
      type string {
        length "0..32";
      }
      description "VRF name";
    }
  }

  grouping IPV4-ACL-BAG-NH-INFO {
    description "NH_Info structure";
    leaf next-hop {
      type inet:ipv4-address;
      description "The next hop";
    }
    leaf track-name {
      type string;
      description "Track name";
    }
    leaf status {
      type Bag-acl-nh-status;
      description "The next hop status";
    }
    leaf at-status {
      type Bag-acl-nh-at-status;
      description "The next hop at status";
    }
    leaf is-acl-next-hop-exist {
      type boolean;
      description "The nexthop exist";
    }
  }

  grouping IPV4-ACL-EDM-ACE {
    description "ACLE bag";

    container hw-next-hop-info {
      description "HW Next hop info";
      uses IPV4-ACL-BAG-HW-NH-INFO;
    }
    leaf item-type {
      type Acl-ace;
      description "ACE type (acl, remark)";
    }
    leaf sequence {
      type uint32;
      description "ACLE sequence number";
    }
    leaf grant {
      type Acl-action;
      description "Permit/deny";
    }
    leaf protocol {
      type uint16;
      description "IPv4 protocol type";
    }
    leaf source-address {
      type inet:ipv4-address;
      description "Source address";
    }
    leaf source-address-mask {
      type inet:ipv4-address;
      description "Source mask";
    }
    leaf destination-address {
      type inet:ipv4-address;
      description "Destination address";
    }
    leaf destination-address-mask {
      type inet:ipv4-address;
      description "Destination mask";
    }
    leaf source-operator {
      type Acl-port-operator;
      description "Source operator";
    }
    leaf source-port1 {
      type uint16;
      description "Source port 1";
    }
    leaf source-port2 {
      type uint16;
      description "Source port 2";
    }
    leaf sorce-operator {
      type Acl-port-operator;
      description "Deprecated by Source operator";
    }
    leaf sorce-port1 {
      type uint16;
      description "Deprecated by SourcePort1";
    }
    leaf sorce-port2 {
      type uint16;
      description "Deprecated by SourcePort2";
    }
    leaf destination-operator {
      type Acl-port-operator;
      description "Destination operator";
    }
    leaf destination-port1 {
      type uint16;
      description "Destination port 1";
    }
    leaf destination-port2 {
      type uint16;
      description "Destination port 2";
    }
    leaf log-option {
      type Acl-log;
      description "Log option";
    }
    leaf counter-name {
      type string;
      description "Counter name";
    }
    leaf capture {
      type boolean;
      description "Capture option, TRUE if enabled";
    }
    leaf dscp-present {
      type boolean;
      description "DSCP present";
    }
    leaf dscp {
      type uint8;
      description "DSCP or DSCP range start";
    }
    leaf dscp2 {
      type uint8;
      description "DSCP Range End";
    }
    leaf dscp-operator {
      type uint8;
      description "DSCP Operator";
    }
    leaf precedence-present {
      type boolean;
      description "Precedence present";
    }
    leaf precedence {
      type uint8;
      description "Precedence";
    }
    leaf tcp-flags-operator {
      type Acl-tcpflags-operator;
      description "TCP flags operator";
    }
    leaf tcp-flags {
      type uint8;
      description "TCP flags";
    }
    leaf tcp-flags-mask {
      type uint8;
      description "TCP flags mask";
    }
    leaf fragments {
      type uint8;
      description "Fragments";
    }
    leaf port-length-operator {
      type Acl-plen-operator;
      description "Port length operator";
    }
    leaf port-length1 {
      type uint16;
      description "Port length 1";
    }
    leaf port-length2 {
      type uint16;
      description "Port length 2";
    }
    leaf ttl-operator {
      type Acl-ttl-operator;
      description "TTL operator";
    }
    leaf ttl1 {
      type uint16;
      description "TTL 1";
    }
    leaf ttl2 {
      type uint16;
      description "TTL 2";
    }
    leaf no-stats {
      type boolean;
      description "No stats";
    }
    leaf hits {
      type uint64;
      description "Number of hits";
    }
    leaf is-icmp-off {
      type boolean;
      description "True if ICMP off";
    }
    leaf next-hop-type {
      type Bag-acl-nh;
      description "Next hop type";
    }
    leaf remark {
      type string;
      description "Remark String";
    }
    leaf dynamic {
      type boolean;
      description "Is dynamic ACE";
    }
    leaf source-prefix-group {
      type string;
      description "Source prefix object-group";
    }
    leaf destination-prefix-group {
      type string;
      description "Destination prefix object-group";
    }
    leaf source-port-group {
      type string;
      description "Source port object-group";
    }
    leaf destination-port-group {
      type string;
      description "Destination port object-group";
    }
    leaf acl-name {
      type string;
      description "ACL Name";
    }
    leaf sequence-str {
      type string;
      description "Sequence String";
    }

    list next-hop-info {
      max-elements "3";
      description "Next hop info";
      uses IPV4-ACL-BAG-NH-INFO;
    }
  }

  grouping IPV4-PFX-EDM-ACE {
    description "Prefix list entry BAG";
    leaf item-type {
      type Acl-ace;
      description "ACE type (prefix, remark)";
    }
    leaf sequence {
      type uint32;
      description "ACLE sequence number";
    }
    leaf grant {
      type Acl-action;
      description "Grant value permit/deny ";
    }
    leaf prefix {
      type inet:ipv4-address;
      description "Prefix";
    }
    leaf prefix-length {
      type uint32;
      description "Prefix length ";
    }
    leaf operator {
      type Acl-port-operator;
      description "Port Operator";
    }
    leaf minimum-length {
      type uint32;
      description "Min length";
    }
    leaf maximum-length {
      type uint32;
      description "Maximum length";
    }
    leaf hits {
      type uint32;
      description "Number of hits";
    }
    leaf remark {
      type string;
      description "Remark String";
    }
    leaf acl-name {
      type string;
      description "ACL Name";
    }
  }
}
