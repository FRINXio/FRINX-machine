submodule Cisco-IOS-XR-ifmgr-oper-sub1 {

  belongs-to Cisco-IOS-XR-ifmgr-oper {
    prefix Cisco-IOS-XR-ifmgr-oper;
  }

  /*** LINKAGE (IMPORTS / INCLUDES) ***/

  import Cisco-IOS-XR-types { prefix "xr"; }

  include Cisco-IOS-XR-ifmgr-oper-sub2 {
    revision-date 2015-07-30;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ifmgr package operational data.

     Copyright (c) 2013-2016 by Cisco Systems, Inc.
     All rights reserved.";

  revision "2015-07-30" {
    description
      "IOS XR 5.3.2 revision.";
  }

  revision "2015-01-07" {
    description
      "IOS XR 5.3.1 revision.";
  }


  grouping IMDS-IFATTR-BASE-INFO {
    description "Basic interface information";
    leaf interface {
      type xr:Interface-name;
      description "Interface";
    }
    leaf parent-interface {
      type xr:Interface-name;
      description "Parent Interface";
    }
    leaf type {
      type string;
      description "Interface type";
    }
    leaf state {
      type Im-state-enum;
      description "Operational state";
    }
    leaf actual-state {
      type Im-state-enum;
      description
        "Operational state with no translation of error
        disable or shutdown";
    }
    leaf line-state {
      type Im-state-enum;
      description "Line protocol state";
    }
    leaf actual-line-state {
      type Im-state-enum;
      description
        "Line protocol state with no translation of error
        disable or shutdown";
    }
    leaf encapsulation {
      type string;
      description "Interface encapsulation";
    }
    leaf encapsulation-type-string {
      type string {
        length "0..32";
      }
      description "Interface encapsulation description string";
    }
    leaf mtu {
      type uint32;
      units "byte";
      description "MTU in bytes";
    }
    leaf sub-interface-mtu-overhead {
      type uint32;
      description "Subif MTU overhead";
    }
    leaf l2-transport {
      type boolean;
      description "L2 transport";
    }
    leaf bandwidth {
      type uint32;
      description "Interface bandwidth (Kb/s)";
    }
  }
}
