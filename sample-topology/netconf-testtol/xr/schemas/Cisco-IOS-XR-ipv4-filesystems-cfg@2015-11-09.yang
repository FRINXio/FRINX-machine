module Cisco-IOS-XR-ipv4-filesystems-cfg {

  /*** NAMESPACE / PREFIX DEFINITION ***/

  namespace "http://cisco.com/ns/yang"+
    "/Cisco-IOS-XR-ipv4-filesystems-cfg";


  prefix "ipv4-filesystems-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-filesystems package configuration.

     This module contains definitions
     for the following management objects:
       rcp: RCP configuration
       ftp: ftp
       tftp: tftp

     Copyright (c) 2013-2016 by Cisco Systems, Inc.
     All rights reserved.";

  revision "2015-11-09" {
    description
      "IOS XR 6.0 revision.";
  }


  grouping SOURCE-INTERFACE {
    description
      "Common node of ftp-client, tftp-client,
      rcp-client";
    leaf source-interface {
      type xr:Interface-name;
      description
        "Specify interface for source address in
        connections";
    }
  }

  container rcp {
    description "RCP configuration";

    container rcp-client {
      description "RCP client configuration";
      uses SOURCE-INTERFACE;
    }
  }

  container ftp {
    description "ftp";

    container ftp-client {
      description "FTP client configuration";
      leaf passive {
        type empty;
        description "Enable connect using passive mode";
      }
      leaf password {
        type xr:Proprietary-password;
        description "Specify password for ftp connnection";
      }
      leaf anonymous-password {
        type string;
        description
          "Password for anonymous user (ftp server
          dependent)";
      }
      uses SOURCE-INTERFACE;
    }
  }

  container tftp {
    description "tftp";

    container tftp-client {
      description "TFTP client configuration";
      uses SOURCE-INTERFACE;
    }
  }
}
