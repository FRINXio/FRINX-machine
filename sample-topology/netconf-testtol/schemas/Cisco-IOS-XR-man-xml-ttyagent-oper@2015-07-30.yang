module Cisco-IOS-XR-man-xml-ttyagent-oper {

  /*** NAMESPACE / PREFIX DEFINITION ***/

  namespace "http://cisco.com/ns/yang"+
    "/Cisco-IOS-XR-man-xml-ttyagent-oper";


  prefix "man-xml-ttyagent-oper";

  /*** LINKAGE (IMPORTS / INCLUDES) ***/

  import Cisco-IOS-XR-types { prefix "xr"; }

  include Cisco-IOS-XR-man-xml-ttyagent-oper-sub1 {
    revision-date 2015-07-30;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-xml-ttyagent package operational data.

     This module contains definitions
     for the following management objects:
       netconf: NETCONF operational information
       xr-xml: xr xml

     Copyright (c) 2013-2016 by Cisco Systems, Inc.
     All rights reserved.";

  revision "2015-07-30" {
    description
      "Descriptions updated.";
  }

  revision "2015-01-07" {
    description
      "IOS XR 5.3.1 revision.";
  }


  grouping SESSION-TABLE {
    description "Common node of default, tty, ssl";

    container sessions {
      description "sessions information";

      list session {
        key "session-id";
        description "xml sessions information";
        leaf session-id {
          type int32;
          description "Session Id";
        }
        uses XR-XML-SESSION-INFO;
      }
    }
  }

  container netconf {
    config false;
    description "NETCONF operational information";

    container agent {
      description "NETCONF agent operational information";

      container tty {
        description "NETCONF agent over TTY";

        container sessions {
          description "Session information";

          list session {
            key "session-id";
            description "Session information";
            leaf session-id {
              type int32;
              description "Session ID";
            }
            uses XR-XML-SESSION-INFO;
          }
        }
      }
    }
  }

  container xr-xml {
    config false;
    description "xr xml";

    container agent {
      description "XML agents";

      container tty {
        description "TTY sessions information";
        uses SESSION-TABLE;
      }

      container default {
        description "Default sessions information";
        uses SESSION-TABLE;
      }

      container ssl {
        description "SSL sessions information";
        uses SESSION-TABLE;
      }
    }
  }
}
