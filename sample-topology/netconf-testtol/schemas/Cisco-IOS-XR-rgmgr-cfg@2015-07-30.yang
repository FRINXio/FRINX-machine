module Cisco-IOS-XR-rgmgr-cfg {

  /*** NAMESPACE / PREFIX DEFINITION ***/

  namespace "http://cisco.com/ns/yang/Cisco-IOS-XR-rgmgr-cfg";


  prefix "rgmgr-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR rgmgr package configuration.

     This module contains definitions
     for the following management objects:
       redundancy-group-manager: Redundancy Group Manager
         Configuration

     Copyright (c) 2013-2016 by Cisco Systems, Inc.
     All rights reserved.";

  revision "2015-07-30" {
    description
      "Descriptions updated.";
  }

  revision "2015-01-07" {
    description
      "IOS XR 5.3.1 revision.";
  }

  typedef Iccp-mode {
    type enumeration {
      enum singleton {
        value 1;
        description "Run the ICCP group in Singleton mode";
      }
    }
    description "Iccp mode";
  }

  container redundancy-group-manager {
    description "Redundancy Group Manager Configuration";

    container aps {
      description "MR-APS groups";

      container default-redundancy-group {
        description "Default SONET controller backup configuration";
        leaf next-hop-address {
          type inet:ipv4-address-no-zone;
          description "IPv4 address of remote peer";
        }
        leaf backup-interface-name {
          type xr:Interface-name;
          description "Backup interface name";
        }
      }

      container groups {
        description "Redundancy Group Table";

        list group {
          key "group-id";
          description "Redundancy Group Configuration";

          container controllers {
            description "Controller configuration";

            list controller {
              key "controller-name";
              description "none";
              leaf controller-name {
                type xr:Interface-name;
                description "Controller Name";
              }
              leaf next-hop-address {
                type inet:ipv4-address-no-zone;
                description "IPv4 address of remote peer";
              }
              leaf backup-interface-name {
                type xr:Interface-name;
                description "Backup interface name";
              }
            }
          }
          leaf group-id {
            type uint32 {
              range "1..32";
            }
            description "The redundancy group ID";
          }
        }
      }
    }

    container iccp {
      description "ICCP configuration";

      container iccp-groups {
        description "Redundancy Group Table Configuration";

        list iccp-group {
          key "group-number";
          description "Redundancy Group Configuration";

          container backbones {
            description "ICCP backbone configuration";

            list backbone {
              key "backbone-name";
              description "ICCP backbone interface configuration";
              leaf backbone-name {
                type xr:Interface-name;
                description "none";
              }
            }
          }

          container members {
            description "ICCP member configuration";

            list member {
              key "neighbor-address";
              description "ICCP member configuration";
              leaf neighbor-address {
                type inet:ipv4-address-no-zone;
                description "Neighbor IP address";
              }
            }
          }
          leaf isolation-recovery-delay {
            type uint32 {
              range "30..600";
            }
            units "second";
            description "ICCP isolation recovery delay";
          }
          leaf mode {
            type Iccp-mode;
            description "ICCP mode";
          }
          leaf group-number {
            type uint32 {
              range "1..4294967295";
            }
            description "The redundancy icc group number";
          }
        }
      }
    }
    leaf enable {
      type empty;
      description "Enable redundancy group manager";
    }
  }
}
