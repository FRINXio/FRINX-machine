submodule Cisco-IOS-XR-upgrade-fpd-oper-sub1 {

  belongs-to Cisco-IOS-XR-upgrade-fpd-oper {
    prefix Cisco-IOS-XR-upgrade-fpd-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR upgrade-fpd package operational data.

     Copyright (c) 2013-2016 by Cisco Systems, Inc.
     All rights reserved.";

  revision "2015-11-09" {
    description
      "IOS XR 6.0 revision.";
  }

  typedef Fpd-sub1 {
    type enumeration {
      enum fpga1 {
        description "FPGA device";
      }
      enum rommon {
        description "ROMMON device";
      }
      enum rommona {
        description "ROMMONA device";
      }
      enum fabric-loader {
        description "Fabric loader";
      }
      enum fpga2 {
        description "FPGA device";
      }
      enum fpga3 {
        description "FPGA device";
      }
      enum fpga4 {
        description "FPGA device";
      }
      enum fpga5 {
        description "FPGA device";
      }
      enum fpga6 {
        description "FPGA device";
      }
      enum fpga7 {
        description "FPGA device";
      }
      enum fpga8 {
        description "FPGA device";
      }
      enum fpga9 {
        description "FPGA device";
      }
      enum fpga10 {
        description "FPGA device";
      }
      enum fpga11 {
        description "FPGA device";
      }
      enum fpga12 {
        description "FPGA device";
      }
      enum fpga13 {
        description "FPGA device";
      }
      enum fpga14 {
        description "FPGA device";
      }
      enum cpld1 {
        description "CPLD device";
      }
      enum cpld2 {
        description "CPLD device";
      }
      enum cpld3 {
        description "CPLD device";
      }
      enum cpld4 {
        description "CPLD device";
      }
      enum cpld5 {
        description "CPLD device";
      }
      enum cpld6 {
        description "CPLD device";
      }
      enum cbc {
        description "CAN bus controller";
      }
      enum hsbi {
        description "HSBI image";
      }
      enum txpod {
        description "Fabric Tx POD";
      }
      enum rxpod {
        description "Fabric Rx POD";
      }
      enum ibmc {
        description "IBMC";
      }
      enum fsbl {
        description "FSBL";
      }
      enum lnx {
        description "Linux firmware";
      }
      enum fpga15 {
        description "FPGA device";
      }
      enum fpga16 {
        description "FPGA device";
      }
      enum fc-fsbl {
        description "FC FSBL";
      }
      enum fc-lnx {
        description "FC linux firmware";
      }
    }
    description "FPD sub types";
  }
  typedef Fpd1 {
    type enumeration {
      enum spa {
        description "Shared port adapter";
      }
      enum lc {
        description "Line card";
      }
      enum sam {
        description "Service acceleration module";
      }
    }
    description "FPD types";
  }

  grouping FPD-PACKAGE-INFO {
    description "Package information";
    leaf card-type {
      type string;
      description "Card type containing FPD";
    }
    leaf card-description {
      type string;
      description "Card description";
    }
    leaf fpd-type {
      type Fpd1;
      description "FPD type";
    }
    leaf fpd-sub-type {
      type Fpd-sub1;
      description "FPD sub type";
    }
    leaf software-version {
      type string;
      description
        "FPD software version in X.Y format X-Major
        version, Y-Minor version Note: 'Unknown' is
        returned in case the software version of the FPD
        cannot be determined.";
    }
    leaf minimum-required-software-version {
      type string;
      description
        "Minimum required FPD software version in X.Y
        format X-Major version, Y-Minor version Note:
        'Unknown' is returned in case the software
        version of the FPD cannot be determined.";
    }
    leaf minimum-required-hardware-version {
      type string;
      description
        "Minimum required FPD hardware version in X.Y
        format X-Major version, Y-Minor version ";
    }
  }

  grouping FPD-ALL-PACKAGES {
    description "Field programmable device packages";

    list all-package {
      description "List of packages";
      uses FPD-PACKAGE-INFO;
    }
  }

  grouping UPGRADE-FPD-INFO {
    description "XML Oper FPD information";
    leaf card-type {
      type string;
      description "Card type containing FPD";
    }
    leaf hardware-version {
      type string;
      description
        "FPD hardware version inX.Y format. X-Major
        version, Y-Minor version";
    }
    leaf software-version {
      type string;
      description
        "FPD software version in X.Y format X-Major
        version, Y-Minor version Note: 'Unknown' is
        returned in case the software version of the FPD
        cannot be determined.";
    }
    leaf is-upgrade-downgrade {
      type boolean;
      description "If true, upgrade or downgrade";
    }
  }
}
