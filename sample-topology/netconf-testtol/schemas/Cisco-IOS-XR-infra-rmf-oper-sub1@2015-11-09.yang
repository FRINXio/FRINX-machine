submodule Cisco-IOS-XR-infra-rmf-oper-sub1 {

  belongs-to Cisco-IOS-XR-infra-rmf-oper {
    prefix Cisco-IOS-XR-infra-rmf-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-rmf package operational data.

     Copyright (c) 2013-2016 by Cisco Systems, Inc.
     All rights reserved.";

  revision "2015-11-09" {
    description
      "IOS XR 6.0 revision.";
  }


  grouping RED-SUMMARY {
    description "rmf show";
    leaf err-log {
      type string;
      description "Error Log";
    }

    list red-pair {
      description "Redundancy Pair";
      uses RED-SUMMARY-PAIR;
    }
  }

  grouping RED-GROUP-INFO {
    description "RED GROUP INFO";
    leaf active {
      type string;
      description "Active";
    }
    leaf standby {
      type string;
      description "Standby";
    }
    leaf ha-state {
      type string;
      description "HAState";
    }
    leaf nsr-state {
      type string;
      description "NSRState";
    }
  }

  grouping RED-SUMMARY-PAIR {
    description "rmf row show";
    leaf active {
      type string;
      description "Active node name R/S/I";
    }
    leaf standby {
      type string;
      description "Standby node name R/S/I";
    }
    leaf ha-state {
      type string;
      description "High Availability state Ready/Not Ready";
    }
    leaf nsr-state {
      type string;
      description "NSR state Configured/Not Configured";
    }

    list groupinfo {
      description "groupinfo";
      uses RED-GROUP-INFO;
    }
  }

  grouping RED-NODE-INFO {
    description "Node Information";

    container redundancy {
      description "Row information";
      uses RED-SUMMARY-PAIR;
    }
    leaf log {
      type string;
      description "Reload and boot logs";
    }
    leaf active-reboot-reason {
      type string;
      description "Active node reload";
    }
    leaf standby-reboot-reason {
      type string;
      description "Standby node reload";
    }
    leaf err-log {
      type string;
      description "Error Log";
    }
  }
}
