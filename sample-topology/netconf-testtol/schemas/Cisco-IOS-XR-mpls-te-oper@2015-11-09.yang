module Cisco-IOS-XR-mpls-te-oper {

  /*** NAMESPACE / PREFIX DEFINITION ***/

  namespace "http://cisco.com/ns/yang/Cisco-IOS-XR-mpls-te-oper";


  prefix "mpls-te-oper";

  /*** LINKAGE (IMPORTS / INCLUDES) ***/

  import ietf-inet-types { prefix "inet"; }

  import Cisco-IOS-XR-types { prefix "xr"; }

  include Cisco-IOS-XR-mpls-te-oper-sub9 {
    revision-date 2015-11-09;
  }

  include Cisco-IOS-XR-mpls-te-oper-sub8 {
    revision-date 2015-11-09;
  }

  include Cisco-IOS-XR-mpls-te-oper-sub7 {
    revision-date 2015-11-09;
  }

  include Cisco-IOS-XR-mpls-te-oper-sub6 {
    revision-date 2015-11-09;
  }

  include Cisco-IOS-XR-mpls-te-oper-sub5 {
    revision-date 2015-11-09;
  }

  include Cisco-IOS-XR-mpls-te-oper-sub4 {
    revision-date 2015-11-09;
  }

  include Cisco-IOS-XR-mpls-te-oper-sub3 {
    revision-date 2015-11-09;
  }

  include Cisco-IOS-XR-mpls-te-oper-sub2 {
    revision-date 2015-11-09;
  }

  include Cisco-IOS-XR-mpls-te-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-te package operational data.

     This module contains definitions
     for the following management objects:
       mpls-te: MPLS Traffic Engineering operational data
       mpls-lcac-standby: mpls lcac standby
       mpls-lcac: mpls lcac
       mpls-pce: mpls pce
       mpls-pce-stdby: mpls pce stdby
       mpls-tp: mpls tp
       mpls-te-standby: mpls te standby

     Copyright (c) 2013-2016 by Cisco Systems, Inc.
     All rights reserved.";

  revision "2015-11-09" {
    description
      "IOS XR 6.0 revision.";
  }

  typedef Attribute-set-name-length {
    type xr:Cisco-ios-xr-string {
      length "0..64";
    }
    description "Attribute set name length";
  }
  typedef Mpls-te-path {
    type enumeration {
      enum not-set {
        value 0;
        description "Not set";
      }
      enum dynamic {
        value 1;
        description "Dynamic";
      }
      enum explicit-name {
        value 3;
        description "Explicit name";
      }
      enum explicit-id {
        value 4;
        description "Explicit ID";
      }
      enum no-ero {
        value 5;
        description "No ERO";
      }
      enum segment-routing {
        value 6;
        description "Segment Routing";
      }
    }
    description "Mpls te path";
  }
  typedef Oc-mpls-te-tunnel {
    type enumeration {
      enum unknown {
        value 0;
        description "UNKNOWN";
      }
      enum p2p {
        value 1;
        description "P2P";
      }
      enum p2mp {
        value 2;
        description "P2MP";
      }
    }
    description "Oc mpls te tunnel";
  }
  typedef Mpls-te-node {
    type enumeration {
      enum router {
        value 1;
        description "Router";
      }
      enum network {
        value 2;
        description "Network";
      }
    }
    description "Mpls te node";
  }
  typedef Preemption-event-index-range {
    type uint32 {
      range "0..1999";
    }
    description "Preemption event index range";
  }
  typedef Mpls-pce-symbolic-name {
    type xr:Cisco-ios-xr-string {
      length "0..256";
    }
    description "Mpls pce symbolic name";
  }
  typedef Ctype {
    type enumeration {
      enum ctype-null {
        value 0;
        description "CTYPE NULL";
      }
      enum ctype-ipv4 {
        value 1;
        description "CTYPE IPV4";
      }
      enum ctype-ipv4-p2p-tunnel {
        value 7;
        description "CTYPE IPV4 P2P TUNNEL";
      }
      enum ctype-ipv6-p2p-tunnel {
        value 8;
        description "CTYPE IPV6 P2P TUNNEL";
      }
      enum ctype-ipv4-uni {
        value 9;
        description "CTYPE IPV4 UNI";
      }
      enum ctype-ipv4-p2mp-tunnel {
        value 13;
        description "CTYPE IPV4 P2MP TUNNEL";
      }
      enum ctype-ipv6-p2mp-tunnel {
        value 14;
        description "CTYPE IPV6 P2MP TUNNEL";
      }
    }
    description "Ctype";
  }
  typedef Mpls-te-next-hop {
    type enumeration {
      enum egress-resolve {
        value 0;
        description "Egress Resolve";
      }
      enum autoroute-dest {
        value 1;
        description "Autoroute Dest";
      }
    }
    description "Mpls te next hop";
  }
  typedef Mpls-te-attr-set {
    type enumeration {
      enum not-used {
        value 0;
        description "Not used";
      }
      enum static {
        value 1;
        description "Static";
      }
      enum lsp {
        value 2;
        description "LSP";
      }
      enum unassigned {
        value 3;
        description "Unassigned";
      }
      enum auto-backup {
        value 4;
        description "Auto backup";
      }
      enum auto-mesh {
        value 5;
        description "Auto mesh";
      }
      enum xro {
        value 6;
        description "XRO";
      }
      enum p2mp-te {
        value 7;
        description "P2MP TE";
      }
      enum otn-pp {
        value 8;
        description "OTN Path Protection";
      }
      enum p2p-te {
        value 9;
        description "P2P TE";
      }
    }
    description "Mpls te attr set";
  }
  typedef Mesh-group-id {
    type uint32 {
      range "0..4294967295";
    }
    description "Mesh group id";
  }
  typedef Mpls-te-igp-protocol {
    type enumeration {
      enum none {
        value 0;
        description "Not set";
      }
      enum isis {
        value 1;
        description "IS IS";
      }
      enum ospf {
        value 2;
        description "OSPF";
      }
    }
    description "Mpls te igp protocol";
  }

  grouping ADVERTISEMENTS {
    description "Common node of mpls-lcac, mpls-lcac-standby";

    container advertisements {
      description "The advertisement information in MPLS-LCAC";
      uses MPLS-LM-ADVERTISEMENT-INFO;
    }
  }

  grouping MAXIMUM-TUNNELS {
    description "Common node of mpls-te, mpls-te-standby";

    container maximum-tunnels {
      description "MPLS Traffic Engineering Tunnels";
      uses TUNNEL-MAX-INFO;
    }
  }

  grouping ADMISSION-CONTROL {
    description "Common node of mpls-lcac, mpls-lcac-standby";

    container admission-control {
      description "The admission control information in MPLS-LCAC";

      container global {
        description "The global admission control information";
        uses MPLS-LM-ADMISSION-CONTROL-COMMON-INFO;
      }

      container admitted-tunnels {
        description
          "The table of admitted tunnels information in
          MPLS-LCAC";

        list admitted-tunnel {
          key "source-address destination-port source-port"+
            " destination-address extended-tunnel-id"+
            " next-hop-address ctype p2mp-id";
          description
            "The information for a specific admitted tunnel";
          leaf source-address {
            type inet:ipv4-address-no-zone;
            description "The source IP address of the tunnel";
          }
          leaf destination-port {
            type int32;
            description "The tunnel number at the head";
          }
          leaf source-port {
            type int32;
            description
              "The signaling instance number of the tunnel";
          }
          leaf destination-address {
            type inet:ipv4-address-no-zone;
            description "The destination IP address of the tunnel";
          }
          leaf extended-tunnel-id {
            type inet:ipv4-address-no-zone;
            description "Extended tunnel id";
          }
          leaf next-hop-address {
            type inet:ipv4-address-no-zone;
            description "The Next hop IP";
          }
          leaf ctype {
            type Ctype;
            description "C type";
          }
          leaf p2mp-id {
            type int32;
            description "P2MP id";
          }
          uses MPLS-LM-ADMISSION-CONTROL-TUNNEL-INFO;
        }
      }

      container link-interfaces {
        description
          "The global admission control information on
          Interfaces";

        list link-interface {
          key "interface-name";
          description
            "The global admission control information on an
            interface";
          leaf interface-name {
            type xr:Interface-name;
            description "Interface name";
          }
          uses MPLS-LM-ADMISSION-CONTROL-COMMON-INFO;
        }
      }
    }
  }

  grouping WRAP-PROTECTION {
    description "Common node of mpls-te, mpls-te-standby";

    container wrap-protection {
      description
        "Represent all the LSP Wrap Protection info in
        MPLS-TE";

      container protected-lsps {
        description
          "The set of wrap protected LSPs available in
          MPLS-TE";

        list protected-lsp {
          key "source-address destination-address tunnel-id"+
            " extended-tunnel-id lsp-id sub-group-id"+
            " sub-group-originator p2mp-id session-type";
          description
            "Wrap protection info for a given protected LSP";
          leaf source-address {
            type inet:ipv4-address-no-zone;
            description "Source Address";
          }
          leaf destination-address {
            type inet:ipv4-address-no-zone;
            description "Destination Address";
          }
          leaf tunnel-id {
            type int32;
            description "Tunnel ID";
          }
          leaf extended-tunnel-id {
            type inet:ipv4-address-no-zone;
            description "Extended Tunnel ID";
          }
          leaf lsp-id {
            type int32;
            description "LSP ID";
          }
          leaf sub-group-id {
            type int32;
            description "Subgroup ID";
          }
          leaf sub-group-originator {
            type inet:ipv4-address-no-zone;
            description "Subgroup Orig ID";
          }
          leaf p2mp-id {
            type int32;
            description "P2MP ID";
          }
          leaf session-type {
            type Ctype;
            description "Session Type";
          }
          uses MPLS-TE-LSP-WRAP-PROTECTION-BAG;
        }
      }
    }
  }

  grouping DIFF-SERV-TE-CLASSES {
    description "Common node of mpls-te, mpls-te-standby";

    container diff-serv-te-classes {
      description "The configured Diff Serv TE classes";
      uses MPLS-TE-DSTE-CLASSES;
    }
  }

  grouping PEER-TABLE {
    description "Common node of mpls-pce, mpls-pce-stdby";

    container peers {
      description "The set of PCE peers";

      list peer {
        key "peer-address";
        description "A PCE peer";
        leaf peer-address {
          type inet:ipv4-address-no-zone;
          description "The peer address";
        }
        uses PCE-NEIGHBOR-BAG;
      }
    }
  }

  grouping LINK-INFORMATION {
    description "Common node of mpls-lcac, mpls-lcac-standby";

    container link-information {
      description "The interface information in MPLS-LCAC";

      container global {
        description "The global information for all the interfaces";
        uses MPLS-LM-INTERFACE-COMMON-INFO;
      }

      container links {
        description "The table of interfaces in MPLS-LCAC";

        list link {
          key "interface-name";
          description "An interface in MPLS-LCAC";
          leaf interface-name {
            type xr:Interface-name;
            description "Interface name";
          }
          uses MPLS-LM-INTERFACE-LINK-INFO;
        }
      }
    }
  }

  grouping LSP-TABLE {
    description "Common node of mpls-pce, mpls-pce-stdby";

    container lsps {
      description "Table of LSPs";

      list lsp {
        key "symbolic-name";
        description "Information of a LSP from LSPDB";
        leaf symbolic-name {
          type Mpls-pce-symbolic-name;
          description "Symbolic name";
        }
        uses PCE-LSP-BAG;
      }
      uses PCE-LSP-BAG;
    }
  }

  grouping PREEMPTION-EVENT-TABLE {
    description "Common node of mpls-lcac, mpls-lcac-standby";

    container preemption-events {
      description "Preemption event log in MPLS-LCAC";

      list preemption-event {
        key "event-index";
        description "Preemption event";
        leaf event-index {
          type Preemption-event-index-range;
          description "Event index";
        }
        uses MPLS-LM-PREEMPTION-EVENT;
      }
    }
  }

  grouping SIGNALLING-COUNTERS {
    description "Common node of mpls-te, mpls-te-standby";

    container signalling-counters {
      description "TE counters";

      container issu {
        description "MPLS TE ISSU counters";
        uses MPLS-TE-SYNC-COUNT-INFO;
      }

      container heads-counters {
        description "MPLS TE counters signalling heads table";

        list heads-counter {
          key "tunnel-id";
          description "MPLS TE counters signalling head";
          leaf tunnel-id {
            type int32;
            description "tunnel id of last obtained tunnel";
          }
          uses TE-STATS-BAG-VIF;
        }
      }

      container mids-counters {
        description "MPLS TE counters signalling heads table";

        list mids-counter {
          key "source-address destination-address tunnel-id"+
            " extended-tunnel-id lsp-id";
          description "MPLS TE counters signalling mid";
          leaf source-address {
            type inet:ipv4-address-no-zone;
            description "Source Address";
          }
          leaf destination-address {
            type inet:ipv4-address-no-zone;
            description "Destination Address";
          }
          leaf tunnel-id {
            type int32;
            description "tunnel id of last obtained tunnel";
          }
          leaf extended-tunnel-id {
            type inet:ipv4-address-no-zone;
            description "Extended Tunnel ID";
          }
          leaf lsp-id {
            type int32;
            description "LSP ID";
          }
          uses TE-STATS-BAG-LSP;
        }
      }

      container head-signalling-counters {
        description "Sig Head Table TE counters";

        list head-signalling-counter {
          key "ctype tunnel-id";
          description "TE stats";
          leaf ctype {
            type Ctype;
            description "Ctype";
          }
          leaf tunnel-id {
            type int32;
            description "Tunnel ID";
          }
          uses TE-STATS-BAG-VIF;
        }
      }

      container remote-signalling-counters {
        description "Sig mid tail Table TE counters";

        list remote-signalling-counter {
          key "ctype tunnel-id extended-tunnel-id p2mp-id lsp-id"+
            " source-address destination-address"+
            " sub-group-originator sub-group-id";
          description "TE stats";
          leaf ctype {
            type Ctype;
            description "Ctype";
          }
          leaf tunnel-id {
            type int32;
            description "Tunnel ID";
          }
          leaf extended-tunnel-id {
            type inet:ipv4-address-no-zone;
            description "Extended Tunnel ID";
          }
          leaf p2mp-id {
            type int32;
            description "P2MP ID";
          }
          leaf lsp-id {
            type int32;
            description "LSP ID";
          }
          leaf source-address {
            type inet:ipv4-address-no-zone;
            description "Source Address";
          }
          leaf destination-address {
            type inet:ipv4-address-no-zone;
            description "Destination Address";
          }
          leaf sub-group-originator {
            type inet:ipv4-address-no-zone;
            description "Subgroup originator";
          }
          leaf sub-group-id {
            type int32;
            description "Subgroup ID";
          }
          uses TE-STATS-BAG-LSP;
        }
      }

      container tails-counters {
        description "MPLS TE counters signalling heads table";

        list tails-counter {
          key "source-address destination-address tunnel-id"+
            " extended-tunnel-id lsp-id";
          description "MPLS TE counters signalling mid";
          leaf source-address {
            type inet:ipv4-address-no-zone;
            description "Source Address";
          }
          leaf destination-address {
            type inet:ipv4-address-no-zone;
            description "Destination Address";
          }
          leaf tunnel-id {
            type int32;
            description "tunnel id of last obtained tunnel";
          }
          leaf extended-tunnel-id {
            type inet:ipv4-address-no-zone;
            description "Extended Tunnel ID";
          }
          leaf lsp-id {
            type int32;
            description "LSP ID";
          }
          uses TE-STATS-BAG-LSP;
        }
      }

      container signallings {
        description "TE counters";

        list signalling {
          key "ctype tunnel-id extended-tunnel-id p2mp-id lsp-id"+
            " source-address destination-address"+
            " sub-group-originator sub-group-id";
          description "TE Sig";
          leaf ctype {
            type Ctype;
            description "Ctype";
          }
          leaf tunnel-id {
            type int32;
            description "Tunnel ID";
          }
          leaf extended-tunnel-id {
            type inet:ipv4-address-no-zone;
            description "Extended Tunnel ID";
          }
          leaf p2mp-id {
            type int32;
            description "P2MP ID";
          }
          leaf lsp-id {
            type int32;
            description "LSP ID";
          }
          leaf source-address {
            type inet:ipv4-address-no-zone;
            description "Source Address";
          }
          leaf destination-address {
            type inet:ipv4-address-no-zone;
            description "Destination Address";
          }
          leaf sub-group-originator {
            type inet:ipv4-address-no-zone;
            description "Subgroup originator";
          }
          leaf sub-group-id {
            type int32;
            description "Subgroup ID";
          }
          uses TE-STATS-SIG-FILTER;
        }
      }

      container signalling-summary {
        description "Send-Recv count summary for TE Signaling";
        uses TE-STATS-SIG;
      }
    }
  }

  grouping OPEN-CONFIG {
    description "Common node of mpls-te, mpls-te-standby";

    container open-config {
      description "OpenConfig MPLS TE operational data";

      container lsp-states {
        description "Table of LSP State Info";

        list lsp-state {
          key "tunnel-name tunnel-type";
          description "MPLS TE LSP State Info";
          leaf tunnel-name {
            type xr:Cisco-ios-xr-string;
            description "Tunnel Name";
          }
          leaf tunnel-type {
            type Oc-mpls-te-tunnel;
            description "Tunnel Type";
          }
          uses OC-MPLS-TE-LSP-STATE;
        }
      }

      container lsp-counters {
        description "Table of LSP Counters";

        list lsp-counter {
          key "tunnel-name tunnel-type";
          description "MPLS TE LSP Counters";
          leaf tunnel-name {
            type xr:Cisco-ios-xr-string;
            description "Tunnel Name";
          }
          leaf tunnel-type {
            type Oc-mpls-te-tunnel;
            description "Tunnel Type";
          }
          uses OC-MPLS-TE-LSP-COUNTERS;
        }
      }
    }
  }

  grouping STATISTICS {
    description "Common node of mpls-lcac, mpls-lcac-standby";

    container statistics {
      description
        "The interface statistics information in
        MPLS-LCAC";

      container summary {
        description "The statistics summary for all interfaces";
        uses MPLS-LM-STATS-SUMMARY-INFO;
      }

      container statstics-links {
        description
          "The table of statistics interfaces in MPLS-LCAC";

        list statstics-link {
          key "interface-name";
          description "An interface in MPLS-LCAC";
          leaf interface-name {
            type xr:Interface-name;
            description "Interface name";
          }
          uses MPLS-LM-STATS-LINK-INFO;
        }
      }
    }
  }

  grouping TE-PCE-OPER-STATISTICS {
    description
      "Common node of mpls-lcac, mpls-lcac-standbyCommon
      node of mpls-pce, mpls-pce-stdby";

    container statistics {
      description "PCE stats info";
      uses PCE-STATS-BAG;
    }
  }

  grouping PATH-PROTECTION {
    description
      "Common node of mpls-lcac, mpls-lcac-standbyCommon
      node of mpls-pce, mpls-pce-stdbyCommon node of
      mpls-te, mpls-te-standby";

    container path-protection {
      description "MPLS TE path protection info";

      container switchover-log {
        description "MPLS TE path protection info";
        uses TE-PP-SW-LOG-BAG;
      }
    }
  }

  grouping ANNOUNCE-TUNNELS-INFO {
    description "Common node of mpls-te, mpls-te-standby";

    container announce-tunnels-info {
      description
        "Announced tunnels (forwarding adjacency and
        autoroute annonce)";

      container autoroute-announce-table {
        description
          "Autoroute announce and forwarding adjacency
          table";
        uses ANNOUNCE-DEST;
      }

      container all-autoroute-table {
        description
          "Autoroute announce and forwarding adjacency
          table";
        uses ANNOUNCE-DEST;
      }
    }
  }

  grouping ATTRIBUTE-SET-TABLE {
    description "Common node of mpls-te, mpls-te-standby";

    container attribute-sets {
      description "AttributeSet information.";

      list attribute-set {
        key "attribute-set-type attribute-set-name";
        description "MPLS TE attribute-set information";
        leaf attribute-set-type {
          type Mpls-te-attr-set;
          description "Attribute Set Type";
        }
        leaf attribute-set-name {
          type Attribute-set-name-length;
          description "Attribute Set Name";
        }
        uses MPLS-TE-ATTRIBUTE-SET;
      }
    }
  }

  grouping ANNOUNCE-DEST {
    description
      "Common node of autoroute-announce-table,
      all-autoroute-table";

    list announce-dest {
      key "destination-address protocol area igp-id";
      description "Autoroute tunnels per destination information";
      leaf destination-address {
        type inet:ipv4-address-no-zone;
        description "Destination Address";
      }
      leaf protocol {
        type Mpls-te-igp-protocol;
        description "The IGP protocol used by the tunnel";
      }
      leaf area {
        type int32;
        description "Area";
      }
      leaf igp-id {
        type xr:Cisco-ios-xr-string;
        description "IGP Instance ID";
      }
      uses MPLS-TE-ANNOUNCEMENT-DEST-BAG;
    }
  }

  grouping TOPOLOGY-BRIEF-TABLE {
    description "Common node of mpls-te, mpls-te-standby";

    container topology-briefs {
      description "MPLS-TE topology brief table";

      list topology-brief {
        key "protocol igp-id area topology-node-type igp-node-id";
        description "A node in MPLS-TE topoogy brief table";
        leaf protocol {
          type Mpls-te-igp-protocol;
          description "IGP protocol type";
        }
        leaf igp-id {
          type xr:Cisco-ios-xr-string;
          description "IGP instance";
        }
        leaf area {
          type int32;
          description "IGP area";
        }
        leaf topology-node-type {
          type Mpls-te-node;
          description "Node type";
        }
        leaf igp-node-id {
          type string;
          description "IGP Node ID";
        }
        uses MPLS-TE-TOPOLOGY-NODE;
      }
    }
  }

  grouping AUTO-TUNNEL {
    description "Common node of mpls-te, mpls-te-standby";

    container auto-tunnel {
      description "Auto tunnel information.";

      container pcc {
        description
          "Auto tunnel PCC (Path Computation Client)
          information.";

        container summary {
          description "MPLS TE auto-tunnel pcc summary information";
          uses MPLS-TE-AUTOTUN-PCC-SUMMARY-INFO;
        }
      }

      container mesh {
        description "Auto tunnel mesh information.";

        container mesh-groups {
          description "Display auto-tunnel mesh group";

          list mesh-group {
            key "mesh-group-id";
            description
              "Display auto-tunnel mesh group information";
            leaf mesh-group-id {
              type Mesh-group-id;
              description "Mesh group ID";
            }
            uses MPLS-TE-MESHGROUP;
          }
        }

        container statistics {
          description
            "MPLS TE auto-tunnel mesh counters (stats)
            information";
          uses TE-STATS-AUTOMESH;
        }

        container summary {
          description
            "MPLS TE auto-tunnel mesh summary information";
          uses MPLS-TE-AUTOTUN-MESH-SUMMARY-INFO;
        }

        container config {
          description
            "MPLS TE auto-tunnel mesh configuration
            information";
          uses MPLS-TE-AUTOTUN-MESH-CONFIG-INFO;
        }

        container one-hop {
          description "MPLS TE auto-tunnel mesh onehop information";

          container interfaces {
            description "Display auto-tunnel onehop interfaces";

            list interface {
              key "interface-name";
              description
                "Display auto-tunnel mesh onehop interface
                information";
              leaf interface-name {
                type xr:Interface-name;
                description "Interface Name";
              }
              uses MPLS-TE-AUTOMESH-ONEHOP-INTERFACE;
            }
          }

          container statistics {
            description
              "MPLS TE auto-tunnel mesh onehop counters
              (stats) information";
            uses TE-STATS-AUTOMESH;
          }

          container summary {
            description
              "MPLS TE auto-tunnel mesh onehop summary
              information";
            uses MPLS-TE-AUTOTUN-MESH-ONEHOP-SUMMARY-INFO;
          }
        }
      }

      container backup {
        description "Auto tunnel backup information.";

        container tunnels {
          description "auto-tunnel backup information";

          list tunnel {
            key "backup-tunnel-name";
            description
              "Display auto tunnel backup tunnel information";
            leaf backup-tunnel-name {
              type xr:Cisco-ios-xr-string;
              description "Backup tunnel name";
            }
            uses MPLS-TE-AUTOTUN-BACKUP-TUNNEL-INFO;
          }
        }

        container statistics {
          description
            "MPLS TE auto-tunnel backup counters (stats)
            information";
          uses TE-STATS-AUTOBACKUP;
        }

        container summary {
          description
            "MPLS TE auto-tunnel backup summary information";
          uses MPLS-TE-AUTOTUN-BACKUP-SUMMARY-INFO;
        }

        container config {
          description
            "MPLS TE auto-tunnel backup configuration
            information";
          uses MPLS-TE-AUTOTUN-BACKUP-CONFIG-INFO;
        }
      }
    }
  }

  grouping COLLABORATOR-TIMERS {
    description "Common node of mpls-te, mpls-te-standby";

    container collaborator-timers {
      description "TE Collaborator timer status";
      uses MPLS-TE-P2MP-TIMERS-B;
    }
  }

  grouping SOFT-PREEMPTION {
    description
      "Common node of mpls-te, mpls-te-standbyCommon
      node of mpls-te, mpls-te-standby";

    container soft-preemption {
      description "Soft Preemption information.";

      container statistics {
        description "MPLS TE soft preemption stats information";
        uses MPLS-TE-SOFT-PREEMPTION-STATS;
      }
    }
  }

  grouping HARDWARE-OUT-OF-RESOURCES {
    description "Common node of mpls-te, mpls-te-standby";

    container hardware-out-of-resources {
      description "NPU Hardware Out of resources Information";

      container summary {
        description "HW OOR Summary information";
        uses TE-HW-OOR-INFO;
      }
    }
  }

  grouping P2P-P2MP-TUNNEL {
    description "Common node of mpls-te, mpls-te-standby";

    container p2p-p2mp-tunnel {
      description "P2P or P2MP tunnels";

      container tunnel-remote-briefs {
        description
          "Restrict display to P2P or P2MP mid or tail
          tunnels";

        list tunnel-remote-brief {
          key "lsp-id tunnel-id extended-tunnel-id source-address"+
            " ctype destination-address p2mp-id";
          description "P2P or P2MP tunnel that is a mid or tail";
          leaf lsp-id {
            type int32;
            description "LSP ID";
          }
          leaf tunnel-id {
            type int32;
            description "Tunnel ID";
          }
          leaf extended-tunnel-id {
            type inet:ipv4-address-no-zone;
            description "Extended Tunnel ID";
          }
          leaf source-address {
            type inet:ipv4-address-no-zone;
            description "Source Address";
          }
          leaf ctype {
            type Ctype;
            description "Ctype";
          }
          leaf destination-address {
            type inet:ipv4-address-no-zone;
            description "Destination Address";
          }
          leaf p2mp-id {
            type int32;
            description "P2MP ID";
          }
          uses MPLS-TE-P2MP-LSP-BRIEF;
        }
      }

      container tunnel-remotes {
        description
          "Restrict display to P2P or P2MP mid or tail
          tunnels";

        list tunnel-remote {
          key "lsp-id tunnel-id extended-tunnel-id source-address"+
            " ctype destination-address p2mp-id";
          description "P2P or P2MP tunnel that is a mid or tail";
          leaf lsp-id {
            type int32;
            description "LSP ID";
          }
          leaf tunnel-id {
            type int32;
            description "Tunnel ID";
          }
          leaf extended-tunnel-id {
            type inet:ipv4-address-no-zone;
            description "Extended Tunnel ID";
          }
          leaf source-address {
            type inet:ipv4-address-no-zone;
            description "Source Address";
          }
          leaf ctype {
            type Ctype;
            description "Ctype";
          }
          leaf destination-address {
            type inet:ipv4-address-no-zone;
            description "Destination Address";
          }
          leaf p2mp-id {
            type int32;
            description "P2MP ID";
          }
          uses MPLS-TE-P2MP-LSP;
        }
      }

      container nni-tunnels {
        description "GMPLS NNI tunnels";

        list nni-tunnel {
          key "tunnel-id source-address destination-address";
          description "GMPLS-NNI tail tunnel";
          leaf tunnel-id {
            type int32;
            description "Tunnel ID";
          }
          leaf source-address {
            type inet:ipv4-address-no-zone;
            description "Source Address";
          }
          leaf destination-address {
            type inet:ipv4-address-no-zone;
            description "Destination Address";
          }
          uses MPLS-TE-P2MP-TUNNEL-BAG;
        }
      }

      container tunnel-heads {
        description "Restrict display to P2P or P2MP head tunnels";

        list tunnel-head {
          key "tunnel-name";
          description "mpls te p2p or p2mp tunnels";
          leaf tunnel-name {
            type xr:Cisco-ios-xr-string;
            description "Tunnel Name";
          }
          uses MPLS-TE-P2MP-TUNNEL-BAG;
        }
      }
    }
  }

  grouping BFD-NEIGHBOR-TABLE {
    description "Common node of mpls-lcac, mpls-lcac-standby";

    container bfd-neighbors {
      description "BFD Neighbors";

      list bfd-neighbor {
        key "interface-name";
        description "A BFD Neighbor";
        leaf interface-name {
          type xr:Interface-name;
          description "Interface name";
        }
        uses MPLS-LM-BFD-NBRS-LINK-INFO;
      }
    }
  }

  grouping SOFT-PREEMPTION-TABLE {
    description "Common node of mpls-lcac, mpls-lcac-standby";

    container soft-preemptions {
      description
        "The soft preemption information for the TE-links";

      list soft-preemption {
        key "interface-name";
        description "The soft preemption info for a TE-link";
        leaf interface-name {
          type xr:Interface-name;
          description "Interface name";
        }
        uses MPLS-LM-SOFT-PREEMPTION-LINK-INFO;
      }
    }
  }

  grouping TUNNEL-TABLE {
    description "Common node of mpls-pce, mpls-pce-stdby";

    container tunnels {
      description "Table of PCE tunnels";

      list tunnel {
        key "tunnel-name";
        description "Information of a PCE tunnel";
        leaf tunnel-name {
          type xr:Cisco-ios-xr-string;
          description "Tunnel Name";
        }
        uses PCE-TUNNEL-BAG;
      }
      uses PCE-TUNNEL-BAG;
    }
  }

  grouping FAST-REROUTE {
    description "Common node of mpls-te, mpls-te-standby";

    container fast-reroute {
      description "Represent all the fastreroute info in MPLS-TE";

      container backup-tunnels {
        description
          "The set of fastreroute backup tunnels available
          in MPLS-TE";

        list backup-tunnel {
          key "tunnel-name interface-name";
          description "Fastreroute info for a given backup tunnel";
          leaf tunnel-name {
            type xr:Cisco-ios-xr-string;
            description "Backup tunnel name";
          }
          leaf interface-name {
            type xr:Interface-name;
            description "Protected interface name";
          }
          uses MPLS-TE-FASTREROUTE-BAG;
        }
      }

      container protected-interfaces {
        description
          "The set of fastreroute protected interfaces
          available in MPLS-TE";

        list protected-interface {
          key "interface-name backup-tunnel-name";
          description
            "Fastreroute info for a given protected
            interface";
          leaf interface-name {
            type xr:Interface-name;
            description "Protected interface name";
          }
          leaf backup-tunnel-name {
            type xr:Cisco-ios-xr-string;
            description "Backup tunnel name";
          }
          uses MPLS-TE-FASTREROUTE-BAG;
        }
      }

      container protections {
        description
          "The set of fastreroute protected interfaces
          available in MPLS-TE";

        list protection {
          key "source-address destination-address tunnel-id"+
            " extended-tunnel-id lsp-id sub-group-id"+
            " sub-group-originator p2mp-id session-type";
          description
            "Fastreroute info for a given protection
            interface";
          leaf source-address {
            type inet:ipv4-address-no-zone;
            description "Source Address";
          }
          leaf destination-address {
            type inet:ipv4-address-no-zone;
            description "Destination Address";
          }
          leaf tunnel-id {
            type int32;
            description "Tunnel ID";
          }
          leaf extended-tunnel-id {
            type inet:ipv4-address-no-zone;
            description "Extended Tunnel ID";
          }
          leaf lsp-id {
            type int32;
            description "LSP ID";
          }
          leaf sub-group-id {
            type int32;
            description "Subgroup ID";
          }
          leaf sub-group-originator {
            type inet:ipv4-address-no-zone;
            description "Subgroup Orig ID";
          }
          leaf p2mp-id {
            type int32;
            description "P2MP ID";
          }
          leaf session-type {
            type int32;
            description "Session Type";
          }
          uses MPLS-TE-FASTREROUTE-PROTECTION-BAG;
        }
      }

      container promotion {
        description
          "The info about the promotion timer of backup
          tunnels";
        uses MPLS-TE-FASTREROUTE-PROMOTION-BAG;
      }
    }
  }

  grouping TOPOLOGY {
    description "Common node of mpls-te, mpls-te-standby";

    container topology {
      description "The topology information in MPLS-TE";

      container global {
        description
          "Global information about the overall MPLS-TE
          topology";
        uses MPLS-TE-TOPOLOGY-GLOBAL-INFO-BAG;
      }

      container destination-paths {
        description
          "This table models the path calculation
          capabilities in MPLS-TE.A GET operation for the
          complete table will return no entries.See the
          class DestinationPath for more details.";

        list destination-path {
          description
            "A GET operation on this class returns the best
            available path in the TE topology to reach the
            specified destination while satisfying the
            specified constraints.";
          leaf destination-address {
            type inet:ipv4-address-no-zone;
            description "Destination Address";
          }
          leaf affinity-bits {
            type int32;
            description "Affinity Bits";
          }
          leaf affinity-mask {
            type int32;
            description "Affinity Mask";
          }
          leaf setup-priority {
            type int32;
            description "Setup Priority";
          }
          leaf hold-priority {
            type int32;
            description "Hold Priority";
          }
          leaf bandwidth {
            type int32;
            units "kbit/s";
            description "Bandwidth in kbps";
          }
          leaf igp-type {
            type Mpls-te-igp-protocol;
            description "IGP Type";
          }
          leaf igp-instance {
            type xr:Cisco-ios-xr-string;
            description "IGP Instance";
          }
          leaf igp-area {
            type int32;
            description "IGP Area";
          }
          leaf hop-limit {
            type int32;
            description "Hop Limit";
          }
          leaf exclude-srlg-ip-address {
            type inet:ipv4-address-no-zone;
            description "Exclude SRLG IP Address";
          }
          leaf path-type {
            type Mpls-te-path;
            description "Path Type";
          }
          leaf path-id {
            type int32;
            description
              "This is the ID of the explicit path to be
              used for this path calculation query";
          }
          leaf path-name {
            type xr:Cisco-ios-xr-string;
            description
              "This is the name of the explicit path to be
              used for this path calculation query";
          }
          leaf cost-limit {
            type int32;
            description "Cost Limit";
          }
          uses MPLS-TE-TOPOLOGY-PATH-BAG;
        }
      }

      container configured-srlgs {
        description "Set of configured SRLG";

        list configured-srlg {
          key "srlg-number";
          description
            "Configured SRLG value and the addresses using
            it";
          leaf srlg-number {
            type int32;
            description "SRLG Number";
          }
          uses MPLS-TE-TOPO-CFG-SRLG;
        }
      }

      container srlgs {
        description
          "Set of SRLG operational value for the overall
          MPLS-TE topology";

        list srlg {
          key "srlg-number";
          description
            "SRLG operational value for the overall MPLS-TE
            topology";
          leaf srlg-number {
            type int32;
            description "SRLG Number";
          }
          uses MPLS-TE-TOPO-SRLG;
        }
      }

      container path-tunnels {
        description "MPLS-Te topology path info";

        list path-tunnel {
          description
            "MPLS-TE topology path taken by the specified
            tunnel";
          leaf tunnel-id {
            type int32;
            description "Tunnel ID";
          }
          leaf tunnel-name {
            type xr:Cisco-ios-xr-string;
            description "Tunnel name";
          }
          uses MPLS-TE-TOPOLOGY-PATH-BAG;
        }
      }
    }
  }

  grouping TE-PCE-OPER-TOPOLOGY {
    description
      "Common node of mpls-te, mpls-te-standbyCommon
      node of mpls-pce, mpls-pce-stdby";

    container topology {
      description "The topology information in PCE";

      container global {
        description
          "The global information of the overall  topology";
        uses PCE-TOPOLOGY-GLOBAL-INFO-BAG;
      }
    }
  }

  grouping FORWARDING-ADJACENCY-DESTINATION-TABLE {
    description "Common node of mpls-te, mpls-te-standby";

    container forwarding-adjacency-destinations {
      description "Announced Destination tunnel";

      list forwarding-adjacency-destination {
        key "destination-address";
        description "Forwarding Adjacencies for a destination";
        leaf destination-address {
          type inet:ipv4-address-no-zone;
          description "Destination address";
        }
        uses MPLS-TE-FWD-ADJ-BAG;
      }
    }
  }

  grouping LINK-SUMMARY {
    description "Common node of mpls-lcac, mpls-lcac-standby";

    container link-summary {
      description "The global summary for all the interfaces";
      uses MPLS-LM-SUMMARY-COMMON-INFO;
    }
  }

  grouping BANDWIDTH-ALLOCATION {
    description "Common node of mpls-lcac, mpls-lcac-standby";

    container bandwidth-allocation {
      description
        "The bandwidth allocation information in
        MPLS-LCAC";

      container global {
        description
          "Global bandwidth allocation information for all
          interfaces";
        uses MPLS-LM-BW-ALLOC-COMMON-INFO;
      }

      container bandwidth-allocation-links {
        description
          "Per-link bandwidth allocation information in
          MPLS-LCAC";

        list bandwidth-allocation-link {
          key "interface-name";
          description
            "The bandwidth allocation for a given interface";
          leaf interface-name {
            type xr:Interface-name;
            description "Interface name";
          }
          uses MPLS-LM-BW-ALLOC-LINK-INFO;
        }
      }
    }
  }

  grouping TUNNELS {
    description "Common node of mpls-te, mpls-te-standby";

    container tunnels {
      description "Failure protection provided for tunnels";

      container tunnel-flex-lsps {
        description "Flex LSP";

        list tunnel-flex-lsp {
          description "Flex LSP";
          leaf ctype {
            type Ctype;
            description "Ctype";
          }
          leaf tunnel-id {
            type int32;
            description "Tunnel ID";
          }
          leaf tunnel-name {
            type xr:Cisco-ios-xr-string;
            description "Tunnel Name";
          }
          uses MPLS-TE-FLEX-LSP;
        }
      }

      container tunnel-auto-bandwidths {
        description "Auto Bandwidth Brief Table";

        list tunnel-auto-bandwidth {
          key "tunnel-name";
          description "Auto Bandwidth info bag";
          leaf tunnel-name {
            type xr:Cisco-ios-xr-string;
            description "Tunnel Name";
          }
          uses MPLS-TE-TUNNELS-AUTOBW-BRIEF;
        }
      }

      container summary {
        description "Summary of tunnel info";
        uses MPLS-TE-TUNNELS-SUMMARY-INFO-BAG;
      }

      container tunnel-path-protections {
        description "Path protection";

        list tunnel-path-protection {
          description "Path Protection";
          leaf ctype {
            type Ctype;
            description "Ctype";
          }
          leaf tunnel-id {
            type int32;
            description "Tunnel ID";
          }
          leaf tunnel-name {
            type xr:Cisco-ios-xr-string;
            description "Tunnel Name";
          }
          uses MPLS-TE-PATH-PROTECTION;
        }
      }
    }
  }

  grouping IGP-AREA-BRIEF-TABLE {
    description "Common node of mpls-te, mpls-te-standby";

    container igp-area-briefs {
      description "The set of IGP-areas known to MPLS-TE";

      list igp-area-brief {
        key "protocol process-tag";
        description "An IGP instance Brief info";
        leaf protocol {
          type Mpls-te-igp-protocol;
          description "The IGP protocol";
        }
        leaf process-tag {
          type xr:Cisco-ios-xr-string;
          description "IGP Process Tag";
        }
        uses TE-SH-IGP;
      }
    }
  }

  grouping IGP-AREA-TABLE {
    description "Common node of mpls-te, mpls-te-standby";

    container igp-areas {
      description "The set of IGP-areas known to MPLS-TE";

      list igp-area {
        key "protocol process-tag";
        description "An IGP instance";
        leaf protocol {
          type Mpls-te-igp-protocol;
          description "The IGP protocol";
        }
        leaf process-tag {
          type xr:Cisco-ios-xr-string;
          description "IGP Process Tag";
        }
        uses TE-SH-IGP;
      }
    }
  }

  grouping P2MP {
    description "Common node of mpls-te, mpls-te-standby";

    container p2mp {
      description "P2MP Information";

      container tunnel-rewrites {
        description "forwarding-adjacency P2MP Tunnel RW";

        list tunnel-rewrite {
          key "tunnel-id lsp-id ctype";
          description "Display only P2MP Information";
          leaf tunnel-id {
            type int32;
            description "Tunnel ID";
          }
          leaf lsp-id {
            type int32;
            description "LSP ID";
          }
          leaf ctype {
            type Ctype;
            description "Ctype";
          }
          uses MPLS-TE-S2L-TUN-RW-BAG;
        }
      }

      container collaborator-timers {
        description "TE Collaborator timer status";
        uses MPLS-TE-P2MP-TIMERS-B;
      }

      container forwarding-output-label-rewrites {
        description "forwarding-adjacency P2MP Information";

        list forwarding-output-label-rewrite {
          key "tunnel-id lsp-id extended-tunnel-id source-address"+
            " p2mp-id destination-address next-hop-address"+
            " previous-hop-address ctype";
          description "Display only P2MP Information";
          leaf tunnel-id {
            type int32;
            description "Tunnel ID";
          }
          leaf lsp-id {
            type int32;
            description "LSP ID";
          }
          leaf extended-tunnel-id {
            type inet:ipv4-address-no-zone;
            description "extended tunnel ID";
          }
          leaf source-address {
            type inet:ipv4-address-no-zone;
            description "Source Address";
          }
          leaf p2mp-id {
            type int32;
            description "P2MP ID";
          }
          leaf destination-address {
            type inet:ipv4-address-no-zone;
            description "Destination Address";
          }
          leaf next-hop-address {
            type inet:ipv4-address-no-zone;
            description "Next Hop";
          }
          leaf previous-hop-address {
            type inet:ipv4-address-no-zone;
            description "Prev Hop";
          }
          leaf ctype {
            type Ctype;
            description "Ctype";
          }
          uses MPLS-TE-S2L-FORWARDING-BAG;
        }
      }
    }
  }

  grouping NSR {
    description "Common node of mpls-te, mpls-te-standby";

    container nsr {
      description "MPLS TE NSR information";

      container status {
        description "MPLS TE NSR Status information";
        uses TE-NSR-ISSU-STATUS-INFO;
      }

      container detail {
        description "MPLS TE NSR Status information";
        uses TE-NSR-ISSU-STATUS-INFO;
      }
    }
  }

  grouping AFFINITY-MAP {
    description
      "Common node of mpls-te, mpls-te-standbyCommon
      node of mpls-te, mpls-te-standby";

    container affinity-map {
      description "Affinity name to value mapping";
      uses MPLS-TE-AFFINITY-MAP-BAG;
    }
  }

  grouping BFD {
    description "Common node of mpls-te, mpls-te-standby";

    container bfd {
      description "MPLS TE BFD Oper Info";

      container head-infos {
        description "MPLS TE Head BFD Over LSP Table";

        list head-info {
          key "tunnel-name";
          description "MPLS TE Head End BFD Over LSP Info";
          leaf tunnel-name {
            type xr:Cisco-ios-xr-string;
            description "Tunnel Name";
          }
          uses MPLS-TE-HEAD-BFD-VIF-INFO;
        }
      }

      container links {
        description "MPLS TE BFD Info";

        list link {
          key "interface-name";
          description "MPLS TE BFD Info";
          leaf interface-name {
            type xr:Interface-name;
            description "Interface name";
          }
          uses MPLS-LM-BFD-NBRS-LINK-INFO;
        }
      }

      container tail-infos {
        description "MPLS TE Tail BFD Over LSP Table";

        list tail-info {
          description "MPLS TE Tail End BFD Over LSP Info";
          leaf source-address {
            type inet:ipv4-address-no-zone;
            description "Source Address";
          }
          leaf tunnel-id {
            type int32;
            description "Tunnel ID";
          }
          leaf lsp-id {
            type int32;
            description "LSP ID";
          }
          leaf destination-address {
            type inet:ipv4-address-no-zone;
            description "Destination Address";
          }
          leaf extended-tunnel-id {
            type inet:ipv4-address-no-zone;
            description "Extended Tunnel ID";
          }
          leaf ctype {
            type Ctype;
            description "Ctype";
          }
          leaf p2mp-id {
            type int32;
            description "P2MP ID";
          }
          uses MPLS-TE-TAIL-BFD-LSP-INFO;
        }
      }

      container summary {
        description "MPLS TE BFD Summary";
        uses MPLS-TE-BFD-SUMMARY;
      }

      container counters {
        description "MPLS TE BFD Counters";
        uses MPLS-TE-BFD-COUNTERS;
      }
    }
  }

  grouping TOPOLOGY-NODE-TABLE {
    description "Common node of mpls-te, mpls-te-standby";

    container topology-nodes {
      description "A node in the MPLS-TE topology";

      list topology-node {
        key "protocol igp-id area topology-node-type igp-node-id";
        description "A node in the MPLS-TE topology";
        leaf protocol {
          type Mpls-te-igp-protocol;
          description "IGP protocol type";
        }
        leaf igp-id {
          type xr:Cisco-ios-xr-string;
          description "IGP instance";
        }
        leaf area {
          type int32;
          description "IGP area";
        }
        leaf topology-node-type {
          type Mpls-te-node;
          description "Node type";
        }
        leaf igp-node-id {
          type string;
          description "IGP Node ID";
        }
        uses MPLS-TE-TOPOLOGY-NODE;
      }
    }
  }

  grouping NEIGHBOR-TABLE {
    description "Common node of mpls-lcac, mpls-lcac-standby";

    container neighbors {
      description "The neighbor information for the local router";

      list neighbor {
        key "interface-name";
        description
          "The neighbors connected to a particular
          interface";
        leaf interface-name {
          type xr:Interface-name;
          description "Interface name";
        }
        uses MPLS-LM-IGP-NBRS-LINK-INFO;
      }
    }
  }

  grouping GMPLS {
    description
      "Common node of mpls-lcac, mpls-lcac-standbyCommon
      node of mpls-lcac, mpls-lcac-standby";

    container gmpls {
      description "GMPLS data";

      container nni {
        description "GMPLS NNI data";
      }

      container uni {
        description "GMPLS UNI data";
      }
    }
  }

  grouping ISSU {
    description "Common node of mpls-te, mpls-te-standby";

    container issu {
      description "MPLS TE ISSU information";

      container status {
        description "MPLS TE ISSU Status information";
        uses TE-NSR-ISSU-STATUS-INFO;
      }

      container detail {
        description "MPLS TE ISSU Status information";
        uses TE-NSR-ISSU-STATUS-INFO;
      }
    }
  }

  grouping SOFT-PREEMPTION-GLOBAL-INFO {
    description "Common node of mpls-lcac, mpls-lcac-standby";

    container soft-preemption-global-info {
      description "The global soft-preemption information";
      uses MPLS-TE-SOFT-PREEMPTION-GLOBAL-INFO;
    }
  }

  container mpls-te {
    config false;
    description "MPLS Traffic Engineering operational data";

    container segment-routing {
      description "The Segment Routing database in MPLS-TE";

      container srigp-area-infos {
        description "Segment-Routing information about IGP areas";

        list srigp-area-info {
          key "protocol igp-instance area";
          description "A Segment-Routing IGP area information";
          leaf protocol {
            type Mpls-te-igp-protocol;
            description "IGP protocol type";
          }
          leaf igp-instance {
            type xr:Cisco-ios-xr-string;
            description "IGP instance";
          }
          leaf area {
            type int32;
            description "IGP area";
          }
          uses TE-SR-IGP-AREA;
        }
      }

      container sr-node-infos {
        description "Segment-Routing nodes database in MPLS-TE";

        list sr-node-info {
          key "protocol igp-instance area igp-node-id";
          description "A Segment-Routing node information";
          leaf protocol {
            type Mpls-te-igp-protocol;
            description "IGP protocol type";
          }
          leaf igp-instance {
            type xr:Cisco-ios-xr-string;
            description "IGP instance";
          }
          leaf area {
            type int32;
            description "IGP area";
          }
          leaf igp-node-id {
            type string;
            description "Node's IGP ID";
          }
          uses TE-SR-NODE;
        }
      }

      container sr-prefix-infos {
        description "Segment-Routing prefixes database in MPLS-TE";

        list sr-prefix-info {
          key "protocol igp-instance area prefix prefix-length";
          description "A Segment-Routing prefix information";
          leaf protocol {
            type Mpls-te-igp-protocol;
            description "IGP protocol type";
          }
          leaf igp-instance {
            type xr:Cisco-ios-xr-string;
            description "IGP instance";
          }
          leaf area {
            type int32;
            description "IGP area";
          }
          leaf prefix {
            type inet:ipv4-address-no-zone;
            description "Segment-Routing prefix";
          }
          leaf prefix-length {
            type int32;
            description "Prefix' length";
          }
          uses TE-SR-PREFIX;
        }
      }
    }

    container fib-next-hop-routes {
      description "MPLS TE FIB nexthop route database";

      list fib-next-hop-route {
        key "prefix-address";
        description "MPLS TE FIB nexthop route";
        leaf prefix-address {
          type inet:ipv4-address-no-zone;
          description "Prefix Address";
        }
        uses TE-FIB-NH-ROUTE-BAG;
      }
    }

    container next-hop-routes {
      description "MPLS TE nexthop route database";

      list next-hop-route {
        description "MPLS TE nexthop route";
        leaf prefix-address {
          type inet:ipv4-address-no-zone;
          description "Prefix Address";
        }
        leaf prefix-length {
          type xr:Ipv4-prefix-length;
          description "Prefix Length";
        }
        leaf next-hop-type {
          type Mpls-te-next-hop;
          description "Next-hop Route Type";
        }
        uses TE-NEXTHOP-ROUTE;
      }
    }

    container auto-route-destination-entries {
      description
        "MPLS TE autoroute destination table indexed by
        tunnel";

      list auto-route-destination-entry {
        key "tunnel-id";
        description
          "MPLS TE autoroute destination info for one
          tunnel";
        leaf tunnel-id {
          type int32;
          description "Tunnel ID";
        }
        uses TE-TUNNEL-AUTOROUTE-DESTINATIONS;
      }
    }

    container te-mib {
      description "TE MIB information";

      container scalars {
        description "MIB Scalar information";
        uses MPLS-TE-MIB-SCALAR-INFO;
      }
    }
    uses HARDWARE-OUT-OF-RESOURCES;
    uses P2P-P2MP-TUNNEL;
    uses TOPOLOGY-NODE-TABLE;
    uses ANNOUNCE-TUNNELS-INFO;
    uses COLLABORATOR-TIMERS;
    uses AUTO-TUNNEL;
    uses SOFT-PREEMPTION;
    uses FORWARDING-ADJACENCY-DESTINATION-TABLE;
    uses IGP-AREA-TABLE;
    uses WRAP-PROTECTION;
    uses TOPOLOGY;
    uses SIGNALLING-COUNTERS;
    uses DIFF-SERV-TE-CLASSES;
    uses ISSU;
    uses FAST-REROUTE;
    uses ATTRIBUTE-SET-TABLE;
    uses IGP-AREA-BRIEF-TABLE;
    uses TUNNELS;
    uses MAXIMUM-TUNNELS;
    uses PATH-PROTECTION;
    uses P2MP;
    uses OPEN-CONFIG;
    uses BFD;
    uses NSR;
    uses AFFINITY-MAP;
    uses TOPOLOGY-BRIEF-TABLE;
  }

  container mpls-lcac-standby {
    config false;
    description "mpls lcac standby";
    uses NEIGHBOR-TABLE;
    uses PREEMPTION-EVENT-TABLE;
    uses ADVERTISEMENTS;
    uses STATISTICS;
    uses BANDWIDTH-ALLOCATION;
    uses GMPLS;
    uses BFD-NEIGHBOR-TABLE;
    uses LINK-SUMMARY;
    uses LINK-INFORMATION;
    uses ADMISSION-CONTROL;
    uses SOFT-PREEMPTION-GLOBAL-INFO;
    uses SOFT-PREEMPTION-TABLE;
  }

  container mpls-lcac {
    config false;
    description "mpls lcac";
    uses NEIGHBOR-TABLE;
    uses PREEMPTION-EVENT-TABLE;
    uses ADVERTISEMENTS;
    uses STATISTICS;
    uses BANDWIDTH-ALLOCATION;
    uses GMPLS;
    uses BFD-NEIGHBOR-TABLE;
    uses LINK-SUMMARY;
    uses LINK-INFORMATION;
    uses ADMISSION-CONTROL;
    uses SOFT-PREEMPTION-GLOBAL-INFO;
    uses SOFT-PREEMPTION-TABLE;
  }

  container mpls-pce {
    config false;
    description "mpls pce";
    uses LSP-TABLE;
    uses TE-PCE-OPER-STATISTICS;
    uses PEER-TABLE;
    uses TE-PCE-OPER-TOPOLOGY;
    uses TUNNEL-TABLE;
  }

  container mpls-pce-stdby {
    config false;
    description "mpls pce stdby";
    uses LSP-TABLE;
    uses TE-PCE-OPER-STATISTICS;
    uses PEER-TABLE;
    uses TE-PCE-OPER-TOPOLOGY;
    uses TUNNEL-TABLE;
  }

  container mpls-tp {
    config false;
    description "mpls tp";

    container tp-links {
      description "Transport profile links";

      container tp-detail-links {
        description "Detailed table of transport profile links";

        list tp-detail-link {
          key "tp-link-id";
          description
            "Detailed information of transport profile link";
          leaf tp-link-id {
            type int32;
            description "Numeric transport profile link identifier";
          }
          uses MPLS-TE-TP-DETAIL-LINK-INFO;
        }
      }

      container tp-link-summary {
        description "Summary of transport profile links";
        uses MPLS-TE-TP-LINK-SUMMARY-INFO;
      }

      container tp-links {
        description "Table of transport profile links";

        list tp-link {
          key "tp-link-id";
          description "Brief information of transport profile link";
          leaf tp-link-id {
            type int32;
            description "Numeric transport profile link identifier";
          }
          uses MPLS-TE-TP-LINK-INFO;
        }
      }
    }

    container tp-tunnels {
      description "Transport profile tunnels";

      container tp-tunnel-summary {
        description "Summary of transport profile tunnels";
        uses MPLS-TE-TP-TUNNEL-SUMMARY;
      }

      container tp-detail-tunnels {
        description "Detailed table of transport profile tunnels";

        list tp-detail-tunnel {
          key "tp-tunnel-name";
          description
            "Detailed information of transport profile
            tunnel";
          leaf tp-tunnel-name {
            type xr:Cisco-ios-xr-string;
            description "Tunnel name";
          }
          uses MPLS-TE-TP-DETAIL-TUNNEL-INFO;
        }
      }

      container tp-tunnels {
        description "Table of transport profile tunnels";

        list tp-tunnel {
          key "tp-tunnel-name";
          description
            "Brief information of transport profile tunnel";
          leaf tp-tunnel-name {
            type xr:Cisco-ios-xr-string;
            description "Tunnel name";
          }
          uses MPLS-TE-TP-TUNNEL-INFO;
        }
      }
    }

    container tp-midpoints {
      description "Transport profile mid-point";

      container tp-detail-midpoints {
        description
          "Detailed table of transport profile mid-points";

        list tp-detail-midpoint {
          key "tp-midpoint-name";
          description
            "Detailed information of transport profile
            mid-point";
          leaf tp-midpoint-name {
            type xr:Cisco-ios-xr-string;
            description "Mid-point name";
          }
          uses MPLS-TP-DETAIL-MID-INFO;
        }
      }

      container tp-midpoint-summary {
        description "Summary of transport profile mid-points";
        uses MPLS-TP-MID-SUMMARY-INFO;
      }

      container tp-midpoints {
        description "Table of transport profile mid-points";

        list tp-midpoint {
          key "tp-midpoint-name";
          description
            "Brief information of transport profile
            mid-point";
          leaf tp-midpoint-name {
            type xr:Cisco-ios-xr-string;
            description "Mid-point name";
          }
          uses MPLS-TP-MID-INFO;
        }
      }
    }

    container tp-global-parameters {
      description "Transport profile global parameters";
      uses MPLS-TE-TP-GLOBAL-INFO;
    }
  }

  container mpls-te-standby {
    config false;
    description "mpls te standby";
    uses HARDWARE-OUT-OF-RESOURCES;
    uses P2P-P2MP-TUNNEL;
    uses TOPOLOGY-NODE-TABLE;
    uses ANNOUNCE-TUNNELS-INFO;
    uses COLLABORATOR-TIMERS;
    uses AUTO-TUNNEL;
    uses SOFT-PREEMPTION;
    uses FORWARDING-ADJACENCY-DESTINATION-TABLE;
    uses IGP-AREA-TABLE;
    uses WRAP-PROTECTION;
    uses TOPOLOGY;
    uses SIGNALLING-COUNTERS;
    uses DIFF-SERV-TE-CLASSES;
    uses ISSU;
    uses FAST-REROUTE;
    uses ATTRIBUTE-SET-TABLE;
    uses IGP-AREA-BRIEF-TABLE;
    uses TUNNELS;
    uses MAXIMUM-TUNNELS;
    uses PATH-PROTECTION;
    uses P2MP;
    uses OPEN-CONFIG;
    uses BFD;
    uses NSR;
    uses AFFINITY-MAP;
    uses TOPOLOGY-BRIEF-TABLE;
  }
}
