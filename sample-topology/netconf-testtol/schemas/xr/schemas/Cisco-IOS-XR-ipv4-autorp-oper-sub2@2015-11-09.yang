submodule Cisco-IOS-XR-ipv4-autorp-oper-sub2 {

  belongs-to Cisco-IOS-XR-ipv4-autorp-oper {
    prefix Cisco-IOS-XR-ipv4-autorp-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-autorp package operational data.

     Copyright (c) 2013-2016 by Cisco Systems, Inc.
     All rights reserved.";

  revision "2015-11-09" {
    description
      "IOS XR 6.0 revision.";
  }

  typedef Autorp-protocol-mode {
    type enumeration {
      enum sparse {
        value 0;
        description "sparse";
      }
      enum bidirectional {
        value 1;
        description "bidirectional";
      }
    }
    description "Autorp protocol mode";
  }

  grouping AUTORP-CRP-BAG {
    description "Auto-RP Candidate RP entry";
    leaf access-list-name {
      type string;
      description "ACL Name";
    }
    leaf candidate-rp-address {
      type inet:ipv4-address;
      description "Candidate RP IP Address";
    }
    leaf ttl {
      type int32;
      description "TTL";
    }
    leaf announce-period {
      type int32;
      description "Announce Period";
    }
    leaf protocol-mode-xr {
      type Autorp-protocol-mode;
      description "Protocol Mode";
    }
  }
}
