module Cisco-IOS-XR-pmengine-oper {

  /*** NAMESPACE / PREFIX DEFINITION ***/

  namespace "http://cisco.com/ns/yang/Cisco-IOS-XR-pmengine-oper";


  prefix "pmengine-oper";

  /*** LINKAGE (IMPORTS / INCLUDES) ***/

  import Cisco-IOS-XR-types { prefix "xr"; }

  include Cisco-IOS-XR-pmengine-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pmengine package operational data.

     This module contains definitions
     for the following management objects:
       performance-management: performace data
       performance-management-history: performance management history

     Copyright (c) 2013-2016 by Cisco Systems, Inc.
     All rights reserved.";

  revision "2015-11-09" {
    description
      "IOS XR 6.0 revision.";
  }


  container performance-management {
    config false;
    description "performace data";

    container ho-vc {
      description "HO_VC controller performance data";

      container ho-vc-ports {
        description "Port performance data";

        list ho-vc-port {
          key "name";
          description "Port performance data";

          container ho-vc-current {
            description "port current performance data";

            container ho-vc-hour24 {
              description "port current performance data";

              container ho-vc-hour24-paths {
                description "port current performance data";

                list ho-vc-hour24-path {
                  key "number";
                  description "port 24 hour Path performance data";
                  leaf number {
                    type int32;
                    description "channel number";
                  }
                  uses PM-HO-VC-PARAS;
                }
              }
            }

            container ho-vc-minute15 {
              description "port current performance data";

              container ho-vc-minute15-paths {
                description "port current performance data";

                list ho-vc-minute15-path {
                  key "number";
                  description
                    "port 15-minute Path performance data";
                  leaf number {
                    type int32;
                    description "channel number";
                  }
                  uses PM-HO-VC-PARAS;
                }
              }
            }
          }
          leaf name {
            type xr:Interface-name;
            description "Port name";
          }
        }
      }
    }

    container odu {
      description "ODU controller performance data";

      container odu-ports {
        description "Port performance data";

        list odu-port {
          key "name";
          description "Port performance data";

          container odu-current {
            description "port current performance data";

            container odu-minute15 {
              description "port current performance data";

              container odu-minute15gfps {
                description "port current performance data";

                list odu-minute15gfp {
                  key "number";
                  description "port 15-minute otn performance data";
                  leaf number {
                    type int32;
                    description "channel number";
                  }
                  uses PM-GFP-PARAS;
                }
              }

              container odu-minute15prbses {
                description "port current performance data";

                list odu-minute15prbs {
                  key "number";
                  description
                    "port 15-minute prbs performance data";
                  leaf number {
                    type int32;
                    description "channel number";
                  }
                  uses PM-PRBS-PARAS;
                }
              }

              container odu-minute15otns {
                description "port current performance data";

                list odu-minute15otn {
                  key "number";
                  description "port 15-minute otn performance data";
                  leaf number {
                    type int32;
                    description "channel number";
                  }
                  uses PM-OTN-PARAS;
                }
              }
            }

            container odu-hour24 {
              description "port current performance data";

              container odu-hour24prbses {
                description "port 24 hour performance data";

                list odu-hour24prbs {
                  key "number";
                  description "port 24 hour otn performance data";
                  leaf number {
                    type int32;
                    description "channel number";
                  }
                  uses PM-PRBS-PARAS;
                }
              }

              container odu-hour24gfps {
                description "port 24 hour performance data";

                list odu-hour24gfp {
                  key "number";
                  description "port 24 hour otn performance data";
                  leaf number {
                    type int32;
                    description "channel number";
                  }
                  uses PM-GFP-PARAS;
                }
              }

              container odu-hour24otns {
                description "port 24 hour performance data";

                list odu-hour24otn {
                  key "number";
                  description "port 24 hour otn performance data";
                  leaf number {
                    type int32;
                    description "channel number";
                  }
                  uses PM-OTN-PARAS;
                }
              }
            }
          }
          leaf name {
            type xr:Interface-name;
            description "Port name";
          }
        }
      }
    }

    container otu {
      description "OTU controller performance data";

      container otu-ports {
        description "Port performance data";

        list otu-port {
          key "name";
          description "Port performance data";

          container otu-current {
            description "port current performance data";

            container otu-minute15 {
              description "port current performance data";

              container otu-minute15fecs {
                description "port current performance data";

                list otu-minute15fec {
                  key "number";
                  description "port 15-minute fec performance data";
                  leaf number {
                    type int32;
                    description "channel number";
                  }
                  uses PM-FEC-PARAS;
                }
              }

              container otu-minute15otns {
                description "port current performance data";

                list otu-minute15otn {
                  key "number";
                  description "port 15-minute otn performance data";
                  leaf number {
                    type int32;
                    description "channel number";
                  }
                  uses PM-OTN-PARAS;
                }
              }
            }

            container otu-second30 {
              description "port current performance data";

              container otu-second30fecs {
                description "port current performance data";

                list otu-second30fec {
                  key "number";
                  description "port 30-sec fec performance data";
                  leaf number {
                    type int32;
                    description "channel number";
                  }
                  uses PM-FEC-PARAS;
                }
              }

              container otu-second30otns {
                description "port current performance data";

                list otu-second30otn {
                  key "number";
                  description "port 30-sec otn performance data";
                  leaf number {
                    type int32;
                    description "channel number";
                  }
                  uses PM-OTN-PARAS;
                }
              }
            }

            container otu-hour24 {
              description "port current performance data";

              container otu-hour24fecs {
                description "port current performance data";

                list otu-hour24fec {
                  key "number";
                  description "port 24 hour fec performance data";
                  leaf number {
                    type int32;
                    description "channel number";
                  }
                  uses PM-FEC-PARAS;
                }
              }

              container otu-hour24otns {
                description "port 24 hour performance data";

                list otu-hour24otn {
                  key "number";
                  description "port 24 hour otn performance data";
                  leaf number {
                    type int32;
                    description "channel number";
                  }
                  uses PM-OTN-PARAS;
                }
              }
            }
          }
          leaf name {
            type xr:Interface-name;
            description "Port name";
          }
        }
      }
    }

    container stm {
      description "STM controller performance data";

      container stm-ports {
        description "Port performance data";

        list stm-port {
          key "name";
          description "Port performance data";

          container stm-current {
            description "port current performance data";

            container stm-hour24 {
              description "port current performance data";

              container stm-hour24stms {
                description "port current performance data";

                list stm-hour24stm {
                  key "number";
                  description "port 24 hour stm performance data";
                  leaf number {
                    type int32;
                    description "channel number";
                  }
                  uses PM-STM-PARAS;
                }
              }
            }

            container stm-minute15 {
              description "port current performance data";

              container stm-minute15stms {
                description "port current performance data";

                list stm-minute15stm {
                  key "number";
                  description "port 15-minute stm performance data";
                  leaf number {
                    type int32;
                    description "channel number";
                  }
                  uses PM-STM-PARAS;
                }
              }
            }
          }
          leaf name {
            type xr:Interface-name;
            description "Port name";
          }
        }
      }
    }

    container sonet {
      description "SONET controller performance data";

      container sonet-ports {
        description "Port performance data";

        list sonet-port {
          key "name";
          description "Port performance data";

          container sonet-current {
            description "port current performance data";

            container sonet-minute15 {
              description "port current performance data";

              container sonet-minute15-paths {
                description "port current performance data";

                list sonet-minute15-path {
                  key "number";
                  description
                    "port 15-minute Path performance data";
                  leaf number {
                    type int32;
                    description "channel number";
                  }
                  uses PM-SONET-PATH-PARAS;
                }
              }

              container sonet-minute15ocns {
                description "port current performance data";

                list sonet-minute15ocn {
                  key "number";
                  description "port 15-minute ocn performance data";
                  leaf number {
                    type int32;
                    description "channel number";
                  }
                  uses PM-SONET-PARAS;
                }
              }
            }

            container sonet-hour24 {
              description "port current performance data";

              container sonet-hour24ocns {
                description "port current performance data";

                list sonet-hour24ocn {
                  key "number";
                  description "port 24 hour ocn performance data";
                  leaf number {
                    type int32;
                    description "channel number";
                  }
                  uses PM-SONET-PARAS;
                }
              }

              container sonet-hour24-paths {
                description "port current performance data";

                list sonet-hour24-path {
                  key "number";
                  description "port 24 hour Path performance data";
                  leaf number {
                    type int32;
                    description "channel number";
                  }
                  uses PM-SONET-PATH-PARAS;
                }
              }
            }
          }
          leaf name {
            type xr:Interface-name;
            description "Port name";
          }
        }
      }
    }

    container optics {
      description "OPTICS controller performance data";

      container optics-ports {
        description "Port performance data";

        list optics-port {
          key "name";
          description "Port performance data";

          container optics-current {
            description "port current performance data";

            container optics-hour24 {
              description "port current performance data";

              container optics-hour24-optics {
                description "port 24 hour performance data";

                list optics-hour24-optic {
                  key "number";
                  description
                    "port 24 hour optics performance data";
                  leaf number {
                    type int32;
                    description "channel number";
                  }
                  uses PM-OPTICS-PARAS;
                }
              }

              container optics-hour24fecs {
                description "port current performance data";

                list optics-hour24fec {
                  key "number";
                  description "port 24 hour fec performance data";
                  leaf number {
                    type int32;
                    description "channel number";
                  }
                  uses PM-FEC-PARAS;
                }
              }
            }

            container optics-minute15 {
              description "port current performance data";

              container optics-minute15-optics {
                description "port current performance data";

                list optics-minute15-optic {
                  key "number";
                  description
                    "port 15-minute optics performance data";
                  leaf number {
                    type int32;
                    description "channel number";
                  }
                  uses PM-OPTICS-PARAS;
                }
              }

              container optics-minute15fecs {
                description "port current performance data";

                list optics-minute15fec {
                  key "number";
                  description "port 15-minute fec performance data";
                  leaf number {
                    type int32;
                    description "channel number";
                  }
                  uses PM-FEC-PARAS;
                }
              }
            }

            container optics-second30 {
              description "port current performance data";

              container optics-second30fecs {
                description "port current performance data";

                list optics-second30fec {
                  key "number";
                  description "port 30-second fec performance data";
                  leaf number {
                    type int32;
                    description "channel number";
                  }
                  uses PM-FEC-PARAS;
                }
              }

              container optics-second30-optics {
                description "port current performance data";

                list optics-second30-optic {
                  key "number";
                  description
                    "port 30-second optics performance data";
                  leaf number {
                    type int32;
                    description "channel number";
                  }
                  uses PM-OPTICS-PARAS;
                }
              }
            }
          }
          leaf name {
            type xr:Interface-name;
            description "Port name";
          }
        }
      }
    }

    container sts {
      description "STS controller performance data";

      container sts-ports {
        description "Port performance data";

        list sts-port {
          key "name";
          description "Port performance data";

          container sts-current {
            description "port current performance data";

            container sts-minute15 {
              description "port current performance data";

              container sts-minute15-paths {
                description "port current performance data";

                list sts-minute15-path {
                  key "number";
                  description
                    "port 15-minute Path performance data";
                  leaf number {
                    type int32;
                    description "channel number";
                  }
                  uses PM-SONET-PATH-PARAS;
                }
              }
            }

            container sts-hour24 {
              description "port current performance data";

              container sts-hour24-paths {
                description "port current performance data";

                list sts-hour24-path {
                  key "number";
                  description "port 24 hour Path performance data";
                  leaf number {
                    type int32;
                    description "channel number";
                  }
                  uses PM-SONET-PATH-PARAS;
                }
              }
            }
          }
          leaf name {
            type xr:Interface-name;
            description "Port name";
          }
        }
      }
    }

    container dwdm {
      description "DWDM controller performance data";

      container dwdm-ports {
        description "Port performance data";

        list dwdm-port {
          key "name";
          description "Port performance data";

          container dwdm-current {
            description "port current performance data";

            container dwdm-minute15 {
              description "port current performance data";

              container dwdm-minute15fecs {
                description "port current performance data";

                list dwdm-minute15fec {
                  key "number";
                  description "port 15-minute fec performance data";
                  leaf number {
                    type int32;
                    description "channel number";
                  }
                  uses PM-FEC-PARAS;
                }
              }

              container dwdm-minute15-optics {
                description "port current performance data";

                list dwdm-minute15-optic {
                  key "number";
                  description
                    "port 15-minute optics performance data";
                  leaf number {
                    type int32;
                    description "channel number";
                  }
                  uses PM-OPTICS-PARAS;
                }
              }

              container dwdm-minute15otns {
                description "port current performance data";

                list dwdm-minute15otn {
                  key "number";
                  description "port 15-minute otn performance data";
                  leaf number {
                    type int32;
                    description "channel number";
                  }
                  uses PM-OTN-PARAS;
                }
              }
            }

            container dwdm-hour24 {
              description "port current performance data";

              container dwdm-hour24-optics {
                description "port 24 hour performance data";

                list dwdm-hour24-optic {
                  key "number";
                  description
                    "port 24 hour optics performance data";
                  leaf number {
                    type int32;
                    description "channel number";
                  }
                  uses PM-OPTICS-PARAS;
                }
              }

              container dwdm-hour24fecs {
                description "port current performance data";

                list dwdm-hour24fec {
                  key "number";
                  description "port 24 hour fec performance data";
                  leaf number {
                    type int32;
                    description "channel number";
                  }
                  uses PM-FEC-PARAS;
                }
              }

              container dwdm-hour24otns {
                description "port 24 hour performance data";

                list dwdm-hour24otn {
                  key "number";
                  description "port 24 hour otn performance data";
                  leaf number {
                    type int32;
                    description "channel number";
                  }
                  uses PM-OTN-PARAS;
                }
              }
            }
          }
          leaf name {
            type xr:Interface-name;
            description "Port name";
          }
        }
      }
    }

    container oc {
      description "OC controller performance data";

      container oc-ports {
        description "Port performance data";

        list oc-port {
          key "name";
          description "Port performance data";

          container oc-current {
            description "port current performance data";

            container oc-hour24 {
              description "port current performance data";

              container oc-hour24ocns {
                description "port current performance data";

                list oc-hour24ocn {
                  key "number";
                  description "port 24 hour ocn performance data";
                  leaf number {
                    type int32;
                    description "channel number";
                  }
                  uses PM-SONET-PARAS;
                }
              }
            }

            container oc-minute15 {
              description "port current performance data";

              container oc-minute15ocns {
                description "port current performance data";

                list oc-minute15ocn {
                  key "number";
                  description "port 15-minute ocn performance data";
                  leaf number {
                    type int32;
                    description "channel number";
                  }
                  uses PM-SONET-PARAS;
                }
              }
            }
          }
          leaf name {
            type xr:Interface-name;
            description "Port name";
          }
        }
      }
    }

    container ethernet {
      description "EHERNET controller performance data";

      container ethernet-ports {
        description "Port performance data";

        list ethernet-port {
          key "name";
          description "Port performance data";

          container ethernet-current {
            description "port current performance data";

            container ethernet-second30 {
              description "port current performance data";

              container second30-ethers {
                description
                  "ETHERNET port interval performance data";

                list second30-ether {
                  key "slot-number";
                  description
                    "ETHERNET port 30 second ether performance
                    data";
                  leaf slot-number {
                    type int32;
                    description "interval slot number";
                  }
                  uses PM-ETHERNET-PARAS;
                }
              }
            }

            container ethernet-hour24 {
              description "port current performance data";

              container ethernet-hour24-ether-s {
                description "port current performance data";

                list ethernet-hour24-ether {
                  key "number";
                  description
                    "port 24 hour ethernet performance data";
                  leaf number {
                    type int32;
                    description "channel number";
                  }
                  uses PM-ETHERNET-PARAS;
                }
              }
            }

            container minute15 {
              description "port current performance data";

              container minute15-ethers {
                description
                  "ETHERNET port interval performance data";

                list minute15-ether {
                  key "slot-number";
                  description
                    "ETHERNET port 15-minute ether performance
                    data";
                  leaf slot-number {
                    type int32;
                    description "interval slot number";
                  }
                  uses PM-ETHERNET-PARAS;
                }
              }
            }
          }
          leaf name {
            type xr:Interface-name;
            description "Port name";
          }
        }
      }
    }
  }

  container performance-management-history {
    config false;
    description "performance management history";

    container global {
      description "global History performace data";

      container periodic {
        description "History performace data";

        container sonet-history {
          description "SONET controller History performance data";

          container sonet-port-histories {
            description "Port performance data";

            list sonet-port-history {
              key "name";
              description "Port performance data";

              container sonet-minute15-history {
                description "port current performance data";

                container sonet-minute15ocn-histories {
                  description "port current performance data";

                  list sonet-minute15ocn-history {
                    key "number";
                    description
                      "port 15-minute ocn performance data";

                    container "sonet-minute15ocn-time-line"+
                      "-instances" {
                      description "port current performance data";

                      list sonet-minute15ocn-time-line-instance {
                        key "number";
                        description
                          "port 15-minute otn performance data";
                        leaf number {
                          type int32;
                          description "History Index number";
                        }
                        uses PM-SONET-PARAS;
                      }
                    }
                    leaf number {
                      type int32;
                      description "channel number";
                    }
                  }
                }

                container sonet-minute15-path-histories {
                  description "port current performance data";

                  list sonet-minute15-path-history {
                    key "number";
                    description
                      "port 15-minute Path performance data";

                    container "sonet-minute15-path-time-line"+
                      "-instances" {
                      description "port current performance data";

                      list sonet-minute15-path-time-line-instance {
                        key "number";
                        description
                          "port 15-minute otn performance data";
                        leaf number {
                          type int32;
                          description "History Index number";
                        }
                        uses PM-SONET-PATH-PARAS;
                      }
                    }
                    leaf number {
                      type int32;
                      description "channel number";
                    }
                  }
                }
              }

              container sonet-hour24-history {
                description "port current performance data";

                container sonet-hour24-path-histories {
                  description "port current performance data";

                  list sonet-hour24-path-history {
                    key "number";
                    description
                      "port 24 hour Path performance data";

                    container "sonet-hour24-path-time-line"+
                      "-instances" {
                      description "port current performance data";

                      list sonet-hour24-path-time-line-instance {
                        key "number";
                        description
                          "port 15-minute otn performance data";
                        leaf number {
                          type int32;
                          description "History Index number";
                        }
                        uses PM-SONET-PATH-PARAS;
                      }
                    }
                    leaf number {
                      type int32;
                      description "channel number";
                    }
                  }
                }

                container sonet-hour24ocn-histories {
                  description "port current performance data";

                  list sonet-hour24ocn-history {
                    key "number";
                    description "port 24 hour ocn performance data";

                    container sonet-hour24ocn-time-line-instances {
                      description "port current performance data";

                      list sonet-hour24ocn-time-line-instance {
                        key "number";
                        description
                          "port 15-minute otn performance data";
                        leaf number {
                          type int32;
                          description "History Index number";
                        }
                        uses PM-SONET-PARAS;
                      }
                    }
                    leaf number {
                      type int32;
                      description "channel number";
                    }
                  }
                }
              }
              leaf name {
                type xr:Interface-name;
                description "Port name";
              }
            }
          }
        }

        container sts-history {
          description "STS controller History performance data";

          container sts-port-histories {
            description "Port performance data";

            list sts-port-history {
              key "name";
              description "Port performance data";

              container sts-minute15-history {
                description "port current performance data";

                container sts-minute15-path-histories {
                  description "port current performance data";

                  list sts-minute15-path-history {
                    key "number";
                    description
                      "port 15-minute Path performance data";

                    container "sts-minute15-path-time-line"+
                      "-instances" {
                      description "port current performance data";

                      list sts-minute15-path-time-line-instance {
                        key "number";
                        description
                          "port 15-minute otn performance data";
                        leaf number {
                          type int32;
                          description "History Index number";
                        }
                        uses PM-SONET-PATH-PARAS;
                      }
                    }
                    leaf number {
                      type int32;
                      description "channel number";
                    }
                  }
                }
              }

              container sts-hour24-history {
                description "port current performance data";

                container sts-hour24-path-histories {
                  description "port current performance data";

                  list sts-hour24-path-history {
                    key "number";
                    description
                      "port 24 hour Path performance data";

                    container sts-hour24-path-time-line-instances {
                      description "port current performance data";

                      list sts-hour24-path-time-line-instance {
                        key "number";
                        description
                          "port 15-minute sts performance data";
                        leaf number {
                          type int32;
                          description "History Index number";
                        }
                        uses PM-SONET-PATH-PARAS;
                      }
                    }
                    leaf number {
                      type int32;
                      description "channel number";
                    }
                  }
                }
              }
              leaf name {
                type xr:Interface-name;
                description "Port name";
              }
            }
          }
        }

        container ethernet-history {
          description "EHERNET controller History performance data";

          container ethernet-port-histories {
            description "Port performance data";

            list ethernet-port-history {
              key "name";
              description "Port performance data";

              container ethernet-second30-history {
                description "port current performance data";

                container second30-ether-histories {
                  description
                    "ETHERNET port interval performance data";

                  list second30-ether-history {
                    key "slot-number";
                    description
                      "ETHERNET port 30 sec ether performance
                      data";

                    container second30-ether-time-line-instances {
                      description "port current performance data";

                      list second30-ether-time-line-instance {
                        key "number";
                        description
                          "port 30 sec otn performance data";
                        leaf number {
                          type int32;
                          description "History Index number";
                        }
                        uses PM-ETHERNET-PARAS;
                      }
                    }
                    leaf slot-number {
                      type int32;
                      description "interval slot number";
                    }
                  }
                }
              }

              container ethernet-hour24-history {
                description "port current performance data";

                container ethernet-hour24-ether-histories {
                  description "port current performance data";

                  list ethernet-hour24-ether-history {
                    key "number";
                    description
                      "port 24 hour ethernet performance data";

                    container "ethernet-hour24-ether-time-line"+
                      "-instances" {
                      description "port current performance data";

                      list "ethernet-hour24-ether-time-line"+
                        "-instance" {
                        key "number";
                        description
                          "port 15-minute otn performance data";
                        leaf number {
                          type int32;
                          description "History Index number";
                        }
                        uses PM-ETHERNET-PARAS;
                      }
                    }
                    leaf number {
                      type int32;
                      description "channel number";
                    }
                  }
                }
              }

              container ethernet-minute15-history {
                description "port current performance data";

                container minute15-ether-histories {
                  description
                    "ETHERNET port interval performance data";

                  list minute15-ether-history {
                    key "slot-number";
                    description
                      "ETHERNET port 15-minute ether performance
                      data";

                    container minute15-ether-time-line-instances {
                      description "port current performance data";

                      list minute15-ether-time-line-instance {
                        key "number";
                        description
                          "port 15-minute otn performance data";
                        leaf number {
                          type int32;
                          description "History Index number";
                        }
                        uses PM-ETHERNET-PARAS;
                      }
                    }
                    leaf slot-number {
                      type int32;
                      description "interval slot number";
                    }
                  }
                }
              }
              leaf name {
                type xr:Interface-name;
                description "Port name";
              }
            }
          }
        }

        container dwdm-history {
          description "DWDM controller History performance data";

          container dwdm-port-histories {
            description "Port performance data";

            list dwdm-port-history {
              key "name";
              description "Port performance data";

              container dwdm-minute15-history {
                description "port current performance data";

                container dwdm-minute15otn-histories {
                  description "port current performance data";

                  list dwdm-minute15otn-history {
                    key "number";
                    description
                      "port 15-minute otn performance data";

                    container dwdm-minute15otn-time-line-instances {
                      description "port current performance data";

                      list dwdm-minute15otn-time-line-instance {
                        key "number";
                        description
                          "port 15-minute otn performance data";
                        leaf number {
                          type int32;
                          description "History Index number";
                        }
                        uses PM-OTN-PARAS;
                      }
                    }
                    leaf number {
                      type int32;
                      description "channel number";
                    }
                  }
                }

                container dwdm-minute15fec-histories {
                  description "port current performance data";

                  list dwdm-minute15fec-history {
                    key "number";
                    description
                      "port 15-minute fec performance data";

                    container dwdm-minute15fec-time-line-instances {
                      description "port current performance data";

                      list dwdm-minute15fec-time-line-instance {
                        key "number";
                        description
                          "port 15-minute fec performance data by
                          index";
                        leaf number {
                          type int32;
                          description "History Index number";
                        }
                        uses PM-FEC-PARAS;
                      }
                    }
                    leaf number {
                      type int32;
                      description "channel number";
                    }
                  }
                }

                container dwdm-minute15-optics-histories {
                  description "port current performance data";

                  list dwdm-minute15-optics-history {
                    key "number";
                    description
                      "port 15-minute optics performance data";

                    container "dwdm-minute15-optics-time-line"+
                      "-instances" {
                      description "port current performance data";

                      list dwdm-minute15-optics-time-line-instance {
                        key "number";
                        description
                          "port 15-minute otn performance data";
                        leaf number {
                          type int32;
                          description "History Index number";
                        }
                        uses PM-OPTICS-PARAS;
                      }
                    }
                    leaf number {
                      type int32;
                      description "channel number";
                    }
                  }
                }
              }

              container dwdm-hour24-history {
                description "port current performance data";

                container dwdm-hour24otn-histories {
                  description "port 24 hour performance data";

                  list dwdm-hour24otn-history {
                    key "number";
                    description "port 24 hour otn performance data";

                    container dwdm-hour24otn-time-line-instances {
                      description "port current performance data";

                      list dwdm-hour24otn-time-line-instance {
                        key "number";
                        description
                          "port 15-minute otn performance data";
                        leaf number {
                          type int32;
                          description "History Index number";
                        }
                        uses PM-OTN-PARAS;
                      }
                    }
                    leaf number {
                      type int32;
                      description "channel number";
                    }
                  }
                }

                container dwdm-hour24fec-histories {
                  description "port current performance data";

                  list dwdm-hour24fec-history {
                    key "number";
                    description "port 24 hour fec performance data";

                    container dwdm-hour24fec-time-line-instances {
                      description "port current performance data";

                      list dwdm-hour24fec-time-line-instance {
                        key "number";
                        description
                          "port 15-minute fec performance data by
                          index";
                        leaf number {
                          type int32;
                          description "History Index number";
                        }
                        uses PM-FEC-PARAS;
                      }
                    }
                    leaf number {
                      type int32;
                      description "channel number";
                    }
                  }
                }

                container dwdm-hour24-optics-histories {
                  description "port 24 hour performance data";

                  list dwdm-hour24-optics-history {
                    key "number";
                    description
                      "port 24 hour optics performance data";

                    container "dwdm-hour24-optics-time-line"+
                      "-instances" {
                      description "port current performance data";

                      list dwdm-hour24-optics-time-line-instance {
                        key "number";
                        description
                          "port 15-minute otn performance data";
                        leaf number {
                          type int32;
                          description "History Index number";
                        }
                        uses PM-OPTICS-PARAS;
                      }
                    }
                    leaf number {
                      type int32;
                      description "channel number";
                    }
                  }
                }
              }
              leaf name {
                type xr:Interface-name;
                description "Port name";
              }
            }
          }
        }

        container stm-history {
          description "STM controller History performance data";

          container stm-port-histories {
            description "Port performance data";

            list stm-port-history {
              key "name";
              description "Port performance data";

              container stm-hour24-history {
                description "port current performance data";

                container stm-hour24stm-histories {
                  description "port current performance data";

                  list stm-hour24stm-history {
                    key "number";
                    description "port 24 hour stm performance data";

                    container stm-hour24stm-time-line-instances {
                      description "port current performance data";

                      list stm-hour24stm-time-line-instance {
                        key "number";
                        description
                          "port 15-minute stm performance data";
                        leaf number {
                          type int32;
                          description "History Index number";
                        }
                        uses PM-STM-PARAS;
                      }
                    }
                    leaf number {
                      type int32;
                      description "channel number";
                    }
                  }
                }
              }

              container stm-minute15-history {
                description "port current performance data";

                container stm-minute15stm-histories {
                  description "port current performance data";

                  list stm-minute15stm-history {
                    key "number";
                    description
                      "port 15-minute stm performance data";

                    container stm-minute15stm-time-line-instances {
                      description "port current performance data";

                      list stm-minute15stm-time-line-instance {
                        key "number";
                        description
                          "port 15-minute stm performance data";
                        leaf number {
                          type int32;
                          description "History Index number";
                        }
                        uses PM-STM-PARAS;
                      }
                    }
                    leaf number {
                      type int32;
                      description "channel number";
                    }
                  }
                }
              }
              leaf name {
                type xr:Interface-name;
                description "Port name";
              }
            }
          }
        }

        container odu-history {
          description "ODU controller History performance data";

          container odu-port-histories {
            description "Port performance data";

            list odu-port-history {
              key "name";
              description "Port performance data";

              container odu-hour24-history {
                description "port current performance data";

                container odu-hour24gfp-histories {
                  description "port 24 hour performance data";

                  list odu-hour24gfp-history {
                    key "number";
                    description "port 24 hour otn performance data";

                    container odu-hour24gfp-time-line-instances {
                      description "port current performance data";

                      list odu-hour24gfp-time-line-instance {
                        key "number";
                        description
                          "port 15-minute otn performance data";
                        leaf number {
                          type int32;
                          description "History Index number";
                        }
                        uses PM-GFP-PARAS;
                      }
                    }
                    leaf number {
                      type int32;
                      description "channel number";
                    }
                  }
                }

                container odu-hour24prbs-histories {
                  description "port 24 hour performance data";

                  list odu-hour24prbs-history {
                    key "number";
                    description
                      "port 24 hour prbs performance data";

                    container odu-hour24prbs-time-line-instances {
                      description "port current performance data";

                      list odu-hour24prbs-time-line-instance {
                        key "number";
                        description
                          "port 15-minute prbs performance data";
                        leaf number {
                          type int32;
                          description "History Index number";
                        }
                        uses PM-PRBS-PARAS;
                      }
                    }
                    leaf number {
                      type int32;
                      description "channel number";
                    }
                  }
                }

                container odu-hour24otn-histories {
                  description "port 24 hour performance data";

                  list odu-hour24otn-history {
                    key "number";
                    description "port 24 hour otn performance data";

                    container odu-hour24otn-time-line-instances {
                      description "port current performance data";

                      list odu-hour24otn-time-line-instance {
                        key "number";
                        description
                          "port 15-minute otn performance data";
                        leaf number {
                          type int32;
                          description "History Index number";
                        }
                        uses PM-OTN-PARAS;
                      }
                    }
                    leaf number {
                      type int32;
                      description "channel number";
                    }
                  }
                }
              }

              container odu-minute15-history {
                description "port current performance data";

                container odu-minute15prbs-histories {
                  description "port current performance data";

                  list odu-minute15prbs-history {
                    key "number";
                    description
                      "port 15-minute prbs performance data";

                    container odu-minute15prbs-time-line-instances {
                      description "port current performance data";

                      list odu-minute15prbs-time-line-instance {
                        key "number";
                        description
                          "port 15-minute prbs performance data";
                        leaf number {
                          type int32;
                          description "History Index number";
                        }
                        uses PM-PRBS-PARAS;
                      }
                    }
                    leaf number {
                      type int32;
                      description "channel number";
                    }
                  }
                }

                container odu-minute15gfp-histories {
                  description "port current performance data";

                  list odu-minute15gfp-history {
                    key "number";
                    description
                      "port 15-minute otn performance data";

                    container odu-minute15gfp-time-line-instances {
                      description "port current performance data";

                      list odu-minute15gfp-time-line-instance {
                        key "number";
                        description
                          "port 15-minute otn performance data";
                        leaf number {
                          type int32;
                          description "History Index number";
                        }
                        uses PM-GFP-PARAS;
                      }
                    }
                    leaf number {
                      type int32;
                      description "channel number";
                    }
                  }
                }

                container odu-minute15otn-histories {
                  description "port current performance data";

                  list odu-minute15otn-history {
                    key "number";
                    description
                      "port 15-minute otn performance data";

                    container odu-minute15otn-time-line-instances {
                      description "port current performance data";

                      list odu-minute15otn-time-line-instance {
                        key "number";
                        description
                          "port 15-minute otn performance data";
                        leaf number {
                          type int32;
                          description "History Index number";
                        }
                        uses PM-OTN-PARAS;
                      }
                    }
                    leaf number {
                      type int32;
                      description "channel number";
                    }
                  }
                }
              }
              leaf name {
                type xr:Interface-name;
                description "Port name";
              }
            }
          }
        }

        container otu-history {
          description "OTU controller History performance data";

          container otu-port-histories {
            description "Port performance data";

            list otu-port-history {
              key "name";
              description "Port performance data";

              container otu-second30-history {
                description "port current performance data";

                container otu-second30fec-histories {
                  description "port current performance data";

                  list otu-second30fec-history {
                    key "number";
                    description
                      "port 30-second fec performance data";

                    container otu-second30fec-time-line-instances {
                      description "port current performance data";

                      list otu-second30fec-time-line-instance {
                        key "number";
                        description
                          "port 30-second fec performance data";
                        leaf number {
                          type int32;
                          description "History Index number";
                        }
                        uses PM-FEC-PARAS;
                      }
                    }
                    leaf number {
                      type int32;
                      description "channel number";
                    }
                  }
                }

                container otu-second30otn-histories {
                  description "port current performance data";

                  list otu-second30otn-history {
                    key "number";
                    description
                      "port 30-second otn performance data";

                    container otu-second30otn-time-line-instances {
                      description "port current performance data";

                      list otu-second30otn-time-line-instance {
                        key "number";
                        description
                          "port 30-second otn performance data";
                        leaf number {
                          type int32;
                          description "History Index number";
                        }
                        uses PM-OTN-PARAS;
                      }
                    }
                    leaf number {
                      type int32;
                      description "channel number";
                    }
                  }
                }
              }

              container otu-minute15-history {
                description "port current performance data";

                container otu-minute15fec-histories {
                  description "port current performance data";

                  list otu-minute15fec-history {
                    key "number";
                    description
                      "port 15-minute fec performance data";

                    container otu-minute15fec-time-line-instances {
                      description "port current performance data";

                      list otu-minute15fec-time-line-instance {
                        key "number";
                        description
                          "port 15-minute fec performance data";
                        leaf number {
                          type int32;
                          description "History Index number";
                        }
                        uses PM-FEC-PARAS;
                      }
                    }
                    leaf number {
                      type int32;
                      description "channel number";
                    }
                  }
                }

                container otu-minute15otn-histories {
                  description "port current performance data";

                  list otu-minute15otn-history {
                    key "number";
                    description
                      "port 15-minute otn performance data";

                    container otu-minute15otn-time-line-instances {
                      description "port current performance data";

                      list otu-minute15otn-time-line-instance {
                        key "number";
                        description
                          "port 15-minute otn performance data";
                        leaf number {
                          type int32;
                          description "History Index number";
                        }
                        uses PM-OTN-PARAS;
                      }
                    }
                    leaf number {
                      type int32;
                      description "channel number";
                    }
                  }
                }
              }

              container otu-hour24-history {
                description "port current performance data";

                container otu-hour24otn-histories {
                  description "port 24 hour performance data";

                  list otu-hour24otn-history {
                    key "number";
                    description "port 24 hour otn performance data";

                    container otu-hour24otn-time-line-instances {
                      description "port current performance data";

                      list otu-hour24otn-time-line-instance {
                        key "number";
                        description
                          "port 15-minute otn performance data";
                        leaf number {
                          type int32;
                          description "History Index number";
                        }
                        uses PM-OTN-PARAS;
                      }
                    }
                    leaf number {
                      type int32;
                      description "channel number";
                    }
                  }
                }

                container otu-hour24fec-histories {
                  description "port current performance data";

                  list otu-hour24fec-history {
                    key "number";
                    description "port 24 hour fec performance data";

                    container otu-hour24fec-time-line-instances {
                      description "port current performance data";

                      list otu-hour24fec-time-line-instance {
                        key "number";
                        description
                          "port 15-minute fec performance data";
                        leaf number {
                          type int32;
                          description "History Index number";
                        }
                        uses PM-FEC-PARAS;
                      }
                    }
                    leaf number {
                      type int32;
                      description "channel number";
                    }
                  }
                }
              }
              leaf name {
                type xr:Interface-name;
                description "Port name";
              }
            }
          }
        }

        container ho-vc-history {
          description "HO_VC controller History performance data";

          container ho-vc-port-histories {
            description "Port performance data";

            list ho-vc-port-history {
              key "name";
              description "Port performance data";

              container ho-vc-minute15-history {
                description "port current performance data";

                container ho-vc-minute15-path-histories {
                  description "port current performance data";

                  list ho-vc-minute15-path-history {
                    key "number";
                    description
                      "port 15-minute Path performance data";

                    container "ho-vc-minute15-path-time-line"+
                      "-instances" {
                      description "port current performance data";

                      list ho-vc-minute15-path-time-line-instance {
                        key "number";
                        description
                          "port 15-minute ho_vc performance data";
                        leaf number {
                          type int32;
                          description "History Index number";
                        }
                        uses PM-HO-VC-PARAS;
                      }
                    }
                    leaf number {
                      type int32;
                      description "channel number";
                    }
                  }
                }
              }

              container ho-vc-hour24-history {
                description "port current performance data";

                container ho-vc-hour24-path-histories {
                  description "port current performance data";

                  list ho-vc-hour24-path-history {
                    key "number";
                    description
                      "port 24 hour Path performance data";

                    container "ho-vc-hour24-path-time-line"+
                      "-instances" {
                      description "port current performance data";

                      list ho-vc-hour24-path-time-line-instance {
                        key "number";
                        description
                          "port 15-minute otn performance data";
                        leaf number {
                          type int32;
                          description "History Index number";
                        }
                        uses PM-HO-VC-PARAS;
                      }
                    }
                    leaf number {
                      type int32;
                      description "channel number";
                    }
                  }
                }
              }
              leaf name {
                type xr:Interface-name;
                description "Port name";
              }
            }
          }
        }

        container optics-history {
          description "OPTICS controller History performance data";

          container optics-port-histories {
            description "Port performance data";

            list optics-port-history {
              key "name";
              description "Port performance data";

              container optics-hour24-history {
                description "port current performance data";

                container optics-hour24-optics-histories {
                  description "port 24 hour performance data";

                  list optics-hour24-optics-history {
                    key "number";
                    description
                      "port 24 hour optics performance data";

                    container "optics-hour24-optics-time-line"+
                      "-instances" {
                      description "port current performance data";

                      list optics-hour24-optics-time-line-instance {
                        key "number";
                        description
                          "port 15-minute otn performance data";
                        leaf number {
                          type int32;
                          description "History Index number";
                        }
                        uses PM-OPTICS-PARAS;
                      }
                    }
                    leaf number {
                      type int32;
                      description "channel number";
                    }
                  }
                }

                container optics-hour24fec-histories {
                  description "port current performance data";

                  list optics-hour24fec-history {
                    key "number";
                    description "port 24 hour fec performance data";

                    container optics-hour24fec-time-line-instances {
                      description "port current performance data";

                      list optics-hour24fec-time-line-instance {
                        key "number";
                        description
                          "port 15-minute fec performance data";
                        leaf number {
                          type int32;
                          description "History Index number";
                        }
                        uses PM-FEC-PARAS;
                      }
                    }
                    leaf number {
                      type int32;
                      description "channel number";
                    }
                  }
                }
              }

              container optics-second30-history {
                description "port current performance data";

                container optics-second30-optics-histories {
                  description "port current performance data";

                  list optics-second30-optics-history {
                    key "number";
                    description
                      "port 30-second optics performance data";

                    container "optics-second30-optics-time-line"+
                      "-instances" {
                      description "port current performance data";

                      list "optics-second30-optics-time-line"+
                        "-instance" {
                        key "number";
                        description
                          "port 30 second otn performance data";
                        leaf number {
                          type int32;
                          description "History Index number";
                        }
                        uses PM-OPTICS-PARAS;
                      }
                    }
                    leaf number {
                      type int32;
                      description "channel number";
                    }
                  }
                }

                container optics-second30fec-histories {
                  description "port current performance data";

                  list optics-second30fec-history {
                    key "number";
                    description
                      "port 30-second fec performance data";

                    container "optics-second30fec-time-line"+
                      "-instances" {
                      description "port current performance data";

                      list optics-second30fec-time-line-instance {
                        key "number";
                        description
                          "port sec-30 fec performance data";
                        leaf number {
                          type int32;
                          description "History Index number";
                        }
                        uses PM-FEC-PARAS;
                      }
                    }
                    leaf number {
                      type int32;
                      description "channel number";
                    }
                  }
                }
              }

              container optics-minute15-history {
                description "port current performance data";

                container optics-minute15-optics-histories {
                  description "port current performance data";

                  list optics-minute15-optics-history {
                    key "number";
                    description
                      "port 15-minute optics performance data";

                    container "optics-minute15-optics-time-line"+
                      "-instances" {
                      description "port current performance data";

                      list "optics-minute15-optics-time-line"+
                        "-instance" {
                        key "number";
                        description
                          "port 15-minute otn performance data";
                        leaf number {
                          type int32;
                          description "History Index number";
                        }
                        uses PM-OPTICS-PARAS;
                      }
                    }
                    leaf number {
                      type int32;
                      description "channel number";
                    }
                  }
                }

                container optics-minute15fec-histories {
                  description "port current performance data";

                  list optics-minute15fec-history {
                    key "number";
                    description
                      "port 15-minute fec performance data";

                    container "optics-minute15fec-time-line"+
                      "-instances" {
                      description "port current performance data";

                      list optics-minute15fec-time-line-instance {
                        key "number";
                        description
                          "port 15-minute fec performance data";
                        leaf number {
                          type int32;
                          description "History Index number";
                        }
                        uses PM-FEC-PARAS;
                      }
                    }
                    leaf number {
                      type int32;
                      description "channel number";
                    }
                  }
                }
              }
              leaf name {
                type xr:Interface-name;
                description "Port name";
              }
            }
          }
        }

        container oc-history {
          description "OC controller History performance data";

          container oc-port-histories {
            description "Port performance data";

            list oc-port-history {
              key "name";
              description "Port performance data";

              container oc-hour24-history {
                description "port current performance data";

                container oc-hour24ocn-histories {
                  description "port current performance data";

                  list oc-hour24ocn-history {
                    key "number";
                    description "port 24 hour ocn performance data";

                    container oc-hour24ocn-time-line-instances {
                      description "port current performance data";

                      list oc-hour24ocn-time-line-instance {
                        key "number";
                        description
                          "port 15-minute otn performance data";
                        leaf number {
                          type int32;
                          description "History Index number";
                        }
                        uses PM-SONET-PARAS;
                      }
                    }
                    leaf number {
                      type int32;
                      description "channel number";
                    }
                  }
                }
              }

              container oc-minute15-history {
                description "port current performance data";

                container oc-minute15ocn-histories {
                  description "port current performance data";

                  list oc-minute15ocn-history {
                    key "number";
                    description
                      "port 15-minute ocn performance data";

                    container oc-minute15ocn-time-line-instances {
                      description "port current performance data";

                      list oc-minute15ocn-time-line-instance {
                        key "number";
                        description
                          "port 15-minute ocn performance data";
                        leaf number {
                          type int32;
                          description "History Index number";
                        }
                        uses PM-SONET-PARAS;
                      }
                    }
                    leaf number {
                      type int32;
                      description "channel number";
                    }
                  }
                }
              }
              leaf name {
                type xr:Interface-name;
                description "Port name";
              }
            }
          }
        }
      }
    }
  }
}
