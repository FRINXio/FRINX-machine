module Cisco-IOS-XR-controller-otu-oper {

  /*** NAMESPACE / PREFIX DEFINITION ***/

  namespace "http://cisco.com/ns/yang"+
    "/Cisco-IOS-XR-controller-otu-oper";


  prefix "controller-otu-oper";

  /*** LINKAGE (IMPORTS / INCLUDES) ***/

  import Cisco-IOS-XR-types { prefix "xr"; }

  include Cisco-IOS-XR-controller-otu-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR controller-otu package operational data.

     This module contains definitions
     for the following management objects:
       otu: OTU operational data

     Copyright (c) 2013-2016 by Cisco Systems, Inc.
     All rights reserved.";

  revision "2015-11-09" {
    description
      "IOS XR 6.0 revision.";
  }


  container otu {
    config false;
    description "OTU operational data";

    container controllers {
      description "All OTU Port operational data";

      list controller {
        key "controller-name";
        description "OTU Port operational data";

        container info {
          description "OTU port operational data";
          uses OTU-PER-PORT-INFO;
        }
        leaf controller-name {
          type xr:Interface-name;
          description "Port name";
        }
      }
    }
  }
}
