module Cisco-IOS-XR-aaa-tacacs-oper {

  /*** NAMESPACE / PREFIX DEFINITION ***/

  namespace "http://cisco.com/ns/yang/Cisco-IOS-XR-aaa-tacacs-oper";


  prefix "aaa-tacacs-oper";

  /*** LINKAGE (IMPORTS / INCLUDES) ***/

  import Cisco-IOS-XR-types { prefix "xr"; }

  import Cisco-IOS-XR-aaa-locald-oper { prefix "a1"; }

  include Cisco-IOS-XR-aaa-tacacs-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-tacacs package operational data.

     This YANG module augments the
       Cisco-IOS-XR-aaa-locald-oper
     module with state data.

     Copyright (c) 2013-2016 by Cisco Systems, Inc.
     All rights reserved.";

  revision "2015-11-09" {
    description
      "IOS XR 6.0 revision.";
  }


  augment "/a1:aaa" {

    container tacacs {
      description "TACACS operational data";

      container requests {
        description "TACACS Active Request List";
        uses TACACS-REQUESTS;
      }

      container servers {
        description "TACACS server Information";
        uses TACACS-SERVERS;
      }

      container server-groups {
        description "TACACS sg Information";
        uses TACACS-SERVER-GROUPS;
      }
    }
    description
      "This augment extends the operational data of
      'Cisco-IOS-XR-aaa-locald-oper'";
  }
}
