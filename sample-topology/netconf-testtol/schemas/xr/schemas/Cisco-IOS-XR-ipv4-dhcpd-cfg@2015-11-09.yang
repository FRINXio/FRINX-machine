module Cisco-IOS-XR-ipv4-dhcpd-cfg {

  /*** NAMESPACE / PREFIX DEFINITION ***/

  namespace "http://cisco.com/ns/yang/Cisco-IOS-XR-ipv4-dhcpd-cfg";


  prefix "ipv4-dhcpd-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-dhcpd package configuration.

     This module contains definitions
     for the following management objects:
       ipv4-dhcpd: DHCP IPV4 configuration

     Copyright (c) 2013-2016 by Cisco Systems, Inc.
     All rights reserved.";

  revision "2015-11-09" {
    description
      "IOS XR 6.0 revision.";
  }

  typedef Ipv4dhcpd-giaddr-policy {
    type enumeration {
      enum keep {
        value 0;
        description "Keep";
      }
      enum replace {
        value 1;
        description "Replace";
      }
      enum drop {
        value 2;
        description "Drop";
      }
    }
    description "Ipv4dhcpd giaddr policy";
  }
  typedef Ipv4dhcpd-broadcast-flag-policy {
    type enumeration {
      enum ignore {
        value 0;
        description "Ignore";
      }
      enum check {
        value 1;
        description "check";
      }
      enum unicast-always {
        value 2;
        description "Unicast always";
      }
    }
    description "Ipv4dhcpd broadcast flag policy";
  }
  typedef Ipv4dhcpd-mode {
    type enumeration {
      enum base {
        value 0;
        description "Base";
      }
      enum relay {
        value 1;
        description "Relay";
      }
      enum snoop {
        value 2;
        description "Snoop";
      }
      enum server {
        value 3;
        description "Server";
      }
      enum proxy {
        value 4;
        description "Proxy";
      }
      enum base2 {
        value 5;
        description "Base2";
      }
    }
    description "Ipv4dhcpd mode";
  }
  typedef Ipv4dhcpd-relay-info-optionvpn-mode {
    type enumeration {
      enum rfc {
        value 0;
        description "RFC";
      }
      enum cisco {
        value 1;
        description "Cisco";
      }
    }
    description "Ipv4dhcpd relay info optionvpn mode";
  }
  typedef Ipv4dhcpd-fmt {
    type enumeration {
      enum no-format {
        value 0;
        description "Not a Format String";
      }
      enum format {
        value 1;
        description "Format String";
      }
    }
    description "Ipv4dhcpd fmt";
  }
  typedef Ipv4dhcpd-relay-info-option-policy {
    type enumeration {
      enum replace {
        value 0;
        description "Replace";
      }
      enum keep {
        value 1;
        description "Keep";
      }
      enum drop {
        value 2;
        description "Drop";
      }
      enum encapsulate {
        value 3;
        description "Encapsulate";
      }
    }
    description "Ipv4dhcpd relay info option policy";
  }
  typedef Ipv4dhcpd-fmt-specifier {
    type enumeration {
      enum physical-chassis {
        value 1;
        description "Physical chassis";
      }
      enum physical-slot {
        value 2;
        description "Physical slot";
      }
      enum physical-sub-slot {
        value 3;
        description "Physical sub-slot";
      }
      enum physical-port {
        value 4;
        description "Physical port";
      }
      enum physical-sub-port {
        value 5;
        description "Physical sub-port";
      }
      enum inner-vlan-id {
        value 6;
        description "Inner VLAN ID";
      }
      enum outer-vlan-id {
        value 7;
        description "Outer VLAN ID";
      }
      enum l2-interface {
        value 8;
        description "L2 Interface";
      }
    }
    description "Ipv4dhcpd fmt specifier";
  }

  container ipv4-dhcpd {
    description "DHCP IPV4 configuration";

    container vrfs {
      description "VRF Table";

      list vrf {
        key "vrf-name";
        description "VRF table";

        container profile {
          presence "Indicates a profile node is configured.";
          description "Profile name and mode";
          leaf vrf-profile-name {
            type string;
            mandatory true;
            description "Profile name";
          }
          leaf mode {
            type Ipv4dhcpd-mode;
            mandatory true;
            description "Dhcp mode";
          }
        }
        leaf vrf-name {
          type xr:Cisco-ios-xr-string;
          description "VRF Name";
        }
      }
    }

    container profiles {
      description "DHCP IPV4 Profile Table";

      list profile {
        key "profile-name";
        description "DHCP IPV4 Profile";

        container modes {
          description "DHCP IPV4 Profile modes";

          list mode {
            key "mode";
            description "DHCP IPV4 Profile mode";

            container server {
              description "DHCP Server profile";
            }

            container relay {
              description "DHCP Relay profile";

              container gi-addr-policy {
                description "GIADDR policy";
                leaf policy {
                  type Ipv4dhcpd-giaddr-policy;
                  description "GIADDR policy";
                }
              }

              container vrfs {
                description "VRF Helper Addresses";

                list vrf {
                  key "vrf-name";
                  description "VRF Name";

                  container helper-addresses {
                    description "Helper Addresses";

                    list helper-address {
                      key "ip-address";
                      description "Helper Address";
                      leaf ip-address {
                        type inet:ipv4-address-no-zone;
                        description "IPV4 Address";
                      }
                      leaf enable {
                        type empty;
                        description "Enable helper - deprecated";
                      }
                      leaf gateway-address {
                        type inet:ipv4-address-no-zone;
                        description "GatewayAddress";
                      }
                    }
                  }
                  leaf vrf-name {
                    type xr:Cisco-ios-xr-string;
                    description "VRF Name";
                  }
                }
              }

              container relay-information-option {
                description "Relay agent information option";
                leaf vpn-mode {
                  type Ipv4dhcpd-relay-info-optionvpn-mode;
                  description "VPN Mode";
                }
                leaf subscriber-id {
                  type string;
                  description "Subscriber ID";
                }
                leaf insert {
                  type empty;
                  description
                    "Insert Relay Agent Information circuit ID
                    and remote ID suboptions in client
                    requests";
                }
                leaf check {
                  type empty;
                  description
                    "Check Relay Agent Information Option in
                    server reply";
                }
                leaf vpn {
                  type empty;
                  description "Insert VPN options";
                }
                leaf allow-untrusted {
                  type empty;
                  description "Forward untrusted packets";
                }
                leaf policy {
                  type Ipv4dhcpd-relay-info-option-policy;
                  description "Relay information option policy";
                }
              }

              container broadcast-policy {
                description "Broadcast Flag policy";
                leaf policy {
                  type Ipv4dhcpd-broadcast-flag-policy;
                  description "Broadcast flag policy";
                }
              }
            }
            leaf enable {
              type empty;
              description "Enable the DHCP IPV4 Profile mode";
            }
            leaf mode {
              type Ipv4dhcpd-mode;
              description "DHCP IPV4 Profile mode";
            }
          }
        }
        leaf profile-name {
          type xr:Cisco-ios-xr-string;
          description "Profile Name";
        }
      }
    }

    container database {
      description
        "Enable DHCP binding database storage to file
        system";
      leaf proxy {
        type empty;
        description
          "Enable DHCP proxy binding database storage to
          file system";
      }
      leaf server {
        type empty;
        description
          "Enable DHCP server binding database storage to
          file system";
      }
      leaf snoop {
        type empty;
        description
          "Enable DHCP snoop binding database storage to
          file system";
      }
      leaf full-write-interval {
        type uint32 {
          range "1..1440";
        }
        default "10";
        description "Full file write interval (default 10 minutes)";
      }
      leaf incremental-write-interval {
        type uint32 {
          range "1..1440";
        }
        default "1";
        description
          "Incremental file write interval (default 1
          minutes)";
      }
    }

    container interfaces {
      description "DHCP IPV4 Interface Table";

      list interface {
        key "interface-name";
        description "DHCP IPV4 Interface";

        container proxy-interface {
          description "DHCP IPv4 proxy information";

          container dhcp-circuit-id {
            presence "Indicates a dhcp-circuit-id node is"+
              " configured.";
            description "Circuit ID value";
            leaf circuit-id {
              type string;
              mandatory true;
              description "DHCP IPv4 circuit ID value";
            }
            leaf format {
              type Ipv4dhcpd-fmt;
              mandatory true;
              description "Format String";
            }
            leaf argument1 {
              type Ipv4dhcpd-fmt-specifier;
              description "Argument";
            }
            leaf argument2 {
              type Ipv4dhcpd-fmt-specifier;
              description "Argument";
            }
            leaf argument3 {
              type Ipv4dhcpd-fmt-specifier;
              description "Argument";
            }
            leaf argument4 {
              type Ipv4dhcpd-fmt-specifier;
              description "Argument";
            }
            leaf argument5 {
              type Ipv4dhcpd-fmt-specifier;
              description "Argument";
            }
            leaf argument6 {
              type Ipv4dhcpd-fmt-specifier;
              description "Argument";
            }
            leaf argument7 {
              type Ipv4dhcpd-fmt-specifier;
              description "Argument";
            }
            leaf argument8 {
              type Ipv4dhcpd-fmt-specifier;
              description "Argument";
            }
            leaf argument9 {
              type Ipv4dhcpd-fmt-specifier;
              description "Argument";
            }
            leaf argument10 {
              type Ipv4dhcpd-fmt-specifier;
              description "Argument";
            }
            leaf argument11 {
              type Ipv4dhcpd-fmt-specifier;
              description "Argument";
            }
            leaf argument12 {
              type Ipv4dhcpd-fmt-specifier;
              description "Argument";
            }
            leaf argument13 {
              type Ipv4dhcpd-fmt-specifier;
              description "Argument";
            }
            leaf argument14 {
              type Ipv4dhcpd-fmt-specifier;
              description "Argument";
            }
            leaf argument15 {
              type Ipv4dhcpd-fmt-specifier;
              description "Argument";
            }
            leaf argument16 {
              type Ipv4dhcpd-fmt-specifier;
              description "Argument";
            }
          }
          leaf profile {
            type string;
            description "Interface profile name";
          }
        }

        container base-interface {
          description "DHCP IPv4 Base profile information";
          leaf profile {
            type string;
            description "Interface profile name";
          }
        }

        container relay-interface {
          description "DHCP IPv4 relay information";

          container relay-dhcp-circuit-id {
            presence "Indicates a relay-dhcp-circuit-id node is"+
              " configured.";
            description "Circuit ID value";
            leaf circuit-id {
              type string;
              mandatory true;
              description "DHCP IPv4 circuit ID value";
            }
            leaf format {
              type Ipv4dhcpd-fmt;
              mandatory true;
              description "Format String";
            }
            leaf argument1 {
              type Ipv4dhcpd-fmt-specifier;
              description "Argument";
            }
            leaf argument2 {
              type Ipv4dhcpd-fmt-specifier;
              description "Argument";
            }
            leaf argument3 {
              type Ipv4dhcpd-fmt-specifier;
              description "Argument";
            }
            leaf argument4 {
              type Ipv4dhcpd-fmt-specifier;
              description "Argument";
            }
            leaf argument5 {
              type Ipv4dhcpd-fmt-specifier;
              description "Argument";
            }
            leaf argument6 {
              type Ipv4dhcpd-fmt-specifier;
              description "Argument";
            }
            leaf argument7 {
              type Ipv4dhcpd-fmt-specifier;
              description "Argument";
            }
            leaf argument8 {
              type Ipv4dhcpd-fmt-specifier;
              description "Argument";
            }
            leaf argument9 {
              type Ipv4dhcpd-fmt-specifier;
              description "Argument";
            }
            leaf argument10 {
              type Ipv4dhcpd-fmt-specifier;
              description "Argument";
            }
            leaf argument11 {
              type Ipv4dhcpd-fmt-specifier;
              description "Argument";
            }
            leaf argument12 {
              type Ipv4dhcpd-fmt-specifier;
              description "Argument";
            }
            leaf argument13 {
              type Ipv4dhcpd-fmt-specifier;
              description "Argument";
            }
            leaf argument14 {
              type Ipv4dhcpd-fmt-specifier;
              description "Argument";
            }
            leaf argument15 {
              type Ipv4dhcpd-fmt-specifier;
              description "Argument";
            }
            leaf argument16 {
              type Ipv4dhcpd-fmt-specifier;
              description "Argument";
            }
          }
        }

        container profile {
          presence "Indicates a profile node is configured.";
          description "Profile name and mode";
          leaf profile-name {
            type string;
            mandatory true;
            description "Profile name";
          }
          leaf mode {
            type Ipv4dhcpd-mode;
            mandatory true;
            description "DHCP mode";
          }
        }

        container server-interface {
          description "DHCP IPv4 Server information";
          leaf profile {
            type string;
            description "Interface profile name";
          }
        }

        container snoop-interface {
          description "DHCP IPv4 snoop information";

          container snoop-circuit-id {
            description
              "Configure circuit ID for snoop 1. Hex 2.
              ASCII";
            leaf format-type {
              type uint32 {
                range "1..2";
              }
              description "Format type, 1. Hex 2. ASCII";
            }
            leaf circuit-id-value {
              type string;
              description "Enter circuit-id value";
            }
          }
        }
        leaf none {
          type empty;
          description "DHCP IPV4 disabled";
        }
        leaf interface-name {
          type xr:Interface-name;
          description "Interface Name";
        }
      }
    }

    container duplicate-mac-allowed {
      presence "Indicates a duplicate-mac-allowed node is"+
        " configured.";
      description "Allow Duplicate MAC Address";
      leaf duplicate-mac {
        type empty;
        mandatory true;
        description "Duplicate mac is allowed";
      }
      leaf exclude-vlan {
        type empty;
        description "Exclude vlan";
      }
    }

    container rate-limit {
      description "Rate limit ingress packets";
      leaf num-period {
        type uint32 {
          range "1..1000";
        }
        default "200";
        description
          "Rate limiter period in msec (default: 200 msec)";
      }
      leaf num-discover {
        type uint32 {
          range "0..1000";
        }
        default "100";
        description
          "Max DISCOVER packets per rate-limiter period
          (default 100)";
      }
    }
    leaf enable {
      type empty;
      description "DHCP IPV4 configuration";
    }
    leaf allow-client-id-change {
      type empty;
      description
        "For BNG session, allow client id change for a
        client MAC";
    }
  }
}
