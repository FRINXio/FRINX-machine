module Cisco-IOS-XR-infra-rcmd-oper {

  /*** NAMESPACE / PREFIX DEFINITION ***/

  namespace "http://cisco.com/ns/yang/Cisco-IOS-XR-infra-rcmd-oper";


  prefix "infra-rcmd-oper";

  /*** LINKAGE (IMPORTS / INCLUDES) ***/

  import ietf-inet-types { prefix "inet"; }

  import Cisco-IOS-XR-types { prefix "xr"; }

  include Cisco-IOS-XR-infra-rcmd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rcmd package operational data.

     This module contains definitions
     for the following management objects:
       rcmd: Show command for Route Convergence Monitoring &
         Diagnostics

     Copyright (c) 2013-2016 by Cisco Systems, Inc.
     All rights reserved.";

  revision "2015-11-09" {
    description
      "IOS XR 6.0 revision.";
  }


  container rcmd {
    config false;
    description
      "Show command for Route Convergence Monitoring &
      Diagnostics";

    container ospf {
      description "Operational data for OSPF";

      container instances {
        description "Operational data";

        list instance {
          key "instance-name";
          description "Operational data for a particular instance";

          container ipfrr-event-summaries {
            description "OSPF IP-FRR events summary data";

            list ipfrr-event-summary {
              key "event-id";
              description "IP-FRR Event data";
              leaf event-id {
                type int32;
                description "Specific IP-FRR Event";
              }
              uses RCMD-SHOW-IPFRR-EVENT-INFO;
            }
          }

          container prefix-event-statistics {
            description "OSPF Prefix events summary data";

            list prefix-event-statistic {
              key "prefix-info";
              description "Prefix Event statistics";
              leaf prefix-info {
                type inet:ip-prefix;
                description "Events with Prefix";
              }
              uses RCMD-SHOW-PREFIX-INFO;
            }
          }

          container spf-run-summaries {
            description "OSPF SPF run summary data";

            list spf-run-summary {
              key "spf-run-number";
              description "SPF Event data";
              leaf spf-run-number {
                type int32;
                description "Specific SPF run";
              }
              uses RCMD-OSPF-SPF-RUN;
            }
          }

          container ipfrr-event-offlines {
            description "OSPF IP-FRR Event offline data";

            list ipfrr-event-offline {
              key "event-id";
              description
                "Offline operational data for particular OSPF
                IP-FRR Event";
              leaf event-id {
                type int32;
                description "Specific IP-FRR Event";
              }
              uses RCMD-SHOW-IPFRR-EVENT-INFO;
            }
          }

          container spf-run-offlines {
            description "OSPF SPF run offline data";

            list spf-run-offline {
              key "spf-run-number";
              description
                "Offline operational data for particular OSPF
                SPF run";
              leaf spf-run-number {
                type int32;
                description "Specific SPF run";
              }
              uses RCMD-OSPF-SPF-RUN;
            }
          }

          container summary-external-event-summaries {
            description
              "OSPF Summary-External Prefix events summary
              data";

            list summary-external-event-summary {
              key "event-id";
              description "OSPF Summary-External Prefix Event data";
              leaf event-id {
                type int32;
                description "Specific Event ID";
              }
              uses RCMD-SHOW-PREFIX-EVENT;
            }
          }

          container prefix-event-summaries {
            description "OSPF Prefix events summary data";

            list prefix-event-summary {
              key "event-id";
              description "OSPF Prefix Event data";
              leaf event-id {
                type int32;
                description "Specific Event ID";
              }
              uses RCMD-SHOW-PREFIX-EVENT;
            }
          }

          container summary-external-event-offlines {
            description
              "OSPF Summary-External Prefix events offline
              data";

            list summary-external-event-offline {
              key "event-id";
              description
                "Offline operational data for particular OSPF
                Prefix Event";
              leaf event-id {
                type int32;
                description "Specific Event ID";
              }
              uses RCMD-SHOW-PREFIX-EVENT;
            }
          }

          container prefix-event-offlines {
            description "OSPF Prefix events offline data";

            list prefix-event-offline {
              key "event-id";
              description
                "Offline operational data for particular OSPF
                Prefix Event";
              leaf event-id {
                type int32;
                description "Specific Event ID";
              }
              uses RCMD-SHOW-PREFIX-EVENT;
            }
          }

          container summary-external-event-statistics {
            description
              "Summary-External prefix monitoring statistics";
            uses RCMD-SHOW-TYPE357-STATS-INFO;
          }
          leaf instance-name {
            type xr:Cisco-ios-xr-string;
            description
              "Operational data for a particular instance";
          }
        }
      }
    }

    container server {
      description "Server Info";

      container normal {
        description "Server Info";
        uses RCMD-SHOW-SERVER;
      }

      container detail {
        description "Server Info";
        uses RCMD-SHOW-SERVER;
      }
    }

    container node {
      description "Node Info";
      uses RCMD-SHOW-NODE;
    }

    container isis {
      description "Operational data for ISIS";

      container instances {
        description "Operational data";

        list instance {
          key "instance-name";
          description "Operational data for a particular instance";

          container ipfrr-event-summaries {
            description "ISIS IP-FRR events summary data";

            list ipfrr-event-summary {
              key "event-id";
              description "IP-FRR Event data";
              leaf event-id {
                type int32;
                description "Specific IP-FRR Event";
              }
              uses RCMD-SHOW-IPFRR-EVENT-INFO;
            }
          }

          container prefix-event-statistics {
            description "ISIS Prefix events statistics data";

            list prefix-event-statistic {
              key "prefix-info";
              description "Monitoring Statistics";
              leaf prefix-info {
                type inet:ip-prefix;
                description "Events with Prefix";
              }
              uses RCMD-SHOW-PREFIX-INFO;
            }
          }

          container spf-run-summaries {
            description "ISIS SPF run summary data";

            list spf-run-summary {
              key "spf-run-number";
              description "SPF Event data";
              leaf spf-run-number {
                type int32;
                description "Specific SPF run";
              }
              uses RCMD-ISIS-SPF-RUN;
            }
          }

          container ipfrr-event-offlines {
            description "ISIS IP-FRR Event offline data";

            list ipfrr-event-offline {
              key "event-id";
              description
                "Offline operational data for particular ISIS
                IP-FRR Event";
              leaf event-id {
                type int32;
                description "Specific IP-FRR Event";
              }
              uses RCMD-SHOW-IPFRR-EVENT-INFO;
            }
          }

          container spf-run-offlines {
            description "ISIS SPF run offline data";

            list spf-run-offline {
              key "spf-run-number";
              description
                "Offline operational data for particular ISIS
                SPF run";
              leaf spf-run-number {
                type int32;
                description "Specific SPF run";
              }
              uses RCMD-ISIS-SPF-RUN;
            }
          }

          container prefix-event-summaries {
            description "ISIS Prefix events summary data";

            list prefix-event-summary {
              key "event-id";
              description "Prefix Event data";
              leaf event-id {
                type int32;
                description "Specific Event ID";
              }
              uses RCMD-SHOW-PREFIX-EVENT;
            }
          }

          container prefix-event-offlines {
            description "ISIS Prefix events offline data";

            list prefix-event-offline {
              key "event-id";
              description
                "Offline operational data for particular ISIS
                Prefix Event";
              leaf event-id {
                type int32;
                description "Specific Event ID";
              }
              uses RCMD-SHOW-PREFIX-EVENT;
            }
          }

          container lsp-regenerateds {
            description "Regenerated LSP data";

            list lsp-regenerated {
              key "serial-number";
              description "Regenerated LSP data";
              leaf serial-number {
                type int32;
                description "Data for a particular regenerated LSP";
              }
              uses RCMD-REGEN-LSP-INFO;
            }
          }
          leaf instance-name {
            type xr:Cisco-ios-xr-string;
            description
              "Operational data for a particular instance";
          }
        }
      }
    }

    container memory {
      description "Memory Info";
      uses RCMD-SHOW-MEMORY;
    }

    container ldp {
      description "LDP data";

      container sessions {
        description "Session Events";

        list session {
          key "event-id";
          description "Session";
          leaf event-id {
            type int32;
            description "Specific Event ID";
          }
          uses RCMD-SHOW-LDP-SESSION-EVENT;
        }
      }

      container remote-lfa-s {
        description "Remote LFA Coverage Events";

        list remote-lfa {
          key "event-id";
          description "RemoteLFA";
          leaf event-id {
            type int32;
            description "Specific Event ID";
          }
          uses RCMD-SHOW-LDP-RLFA-EVENT;
        }
      }

      container remote-lfa-summaries {
        description "Remote LFA Coverage Events";

        list remote-lfa-summary {
          key "event-id";
          description "Summary operational data for Remote LFA";
          leaf event-id {
            type int32;
            description "Specific Event ID";
          }
          uses RCMD-SHOW-LDP-RLFA-EVENT;
        }
      }
    }

    container intf {
      description "Interface data";

      container events {
        description "Events";

        list event {
          key "event-no";
          description "Events";
          leaf event-no {
            type int32;
            description "Specific Event No.";
          }
          uses RCMD-SHOW-INTF-EVENT;
        }
      }
    }

    container process {
      description "Process information";

      container isis {
        description "ISIS Process Information";
        uses RCMD-SHOW-PROCESS;
      }

      container ospf {
        description "OSPF Process Information";
        uses RCMD-SHOW-PROCESS;
      }

      container ldp {
        description "LDP Process Information";
        uses RCMD-SHOW-PROCESS;
      }
    }
  }
}
